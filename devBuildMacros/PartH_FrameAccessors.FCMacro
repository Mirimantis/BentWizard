# -*- coding: utf-8 -*-
"""Part H of docs/session-frame-accessors.md, driven headlessly.

Opens ``scratch/Frame Accessors Part G.FCStd`` (never modified), saves it as
``scratch/Frame Accessors Part H.FCStd`` and runs:

  H0  give F_Girt_A the full accessor set (Part B's deferred item)
  H1  copy Tenon.MT.001, bind the copy to F_Girt_A, fuse -- change nothing else
  H1b re-point the copy's <<F_Girt_B>> accessor references to <<F_Girt_A>>
      (the strict "references only the frame it is placed on" form)
  H2  an asymmetric adder (tenon centre displaced +1 in X, +1/2 in Y frame-local)
      at both ends: which face does each end favour under the declared
      180-about-Y flip, and under 180-about-X?
  H3  can a native mirror (Part::Mirroring) give the same faces at both ends,
      and does PartDesign::Boolean accept it?

Runs under freecadcmd.exe or from the GUI Macro menu.  Every measurement is
printed as a markdown table and also written to scratch/PartH_results.md.

    freecadcmd.exe "devBuildMacros\\PartH_FrameAccessors.FCMacro"
"""
import os
import sys
import tempfile

import FreeCAD as App
import Part

try:
    HERE = os.path.dirname(os.path.abspath(__file__))
    REPO = os.path.dirname(HERE)
except NameError:  # run from the GUI macro dialog without __file__
    REPO = r"C:\Users\Adam\Documents\Projects\BentWizard"

SCRATCH = os.path.join(REPO, "scratch")
SRC = os.path.join(SCRATCH, "Frame Accessors Part G.FCStd")
OUT_H = os.path.join(SCRATCH, "Frame Accessors Part H.FCStd")
OUT_H1 = os.path.join(SCRATCH, "Frame Accessors Part H1.FCStd")
OUT_XFLIP = os.path.join(SCRATCH, "Frame Accessors Part H (Xflip).FCStd")
RESULTS_MD = os.path.join(SCRATCH, "PartH_results.md")

IN = 25.4
TOL = 1e-6           # mm, for equalities that should be exact
VOL_TOL = 1e-3       # mm^3
PI = 3.141592653589793

LINES = []
CHECKS = []


def out(s=""):
    print(s)
    LINES.append(s)


def check(name, ok, observed):
    CHECKS.append((name, "PASS" if ok else "FAIL", observed))
    out("- %s **%s** -- %s" % ("PASS" if ok else "FAIL", name, observed))
    return ok


def near(a, b, tol=TOL):
    return abs(a - b) <= tol


def inch(v):
    return "%.4f in" % (v / IN)


def fmt_vec(v):
    if v is None:
        return "none"
    return "(%.3f, %.3f, %.3f) mm = (%.4f, %.4f, %.4f) in" % (
        v.x, v.y, v.z, v.x / IN, v.y / IN, v.z / IN)


def face_of(x, y):
    fx = "+X" if x > 1e-6 else ("-X" if x < -1e-6 else "centred X")
    fy = "+Y" if y > 1e-6 else ("-Y" if y < -1e-6 else "centred Y")
    return fx, fy


def by_label(doc, label):
    objs = doc.getObjectsByLabel(label)
    if len(objs) != 1:
        raise RuntimeError("expected exactly one %r, found %d" % (label, len(objs)))
    return objs[0]


ORIGIN_TYPES = ("App::Origin", "App::Line", "App::Plane", "App::Point")


def is_origin_part(o):
    return o.TypeId in ORIGIN_TYPES


# --------------------------------------------------------------------------
# recompute with console capture (headless only; the GUI report view is left alone)

def _capture(fn):
    if App.GuiUp:
        return fn(), ""
    handle = tempfile.NamedTemporaryFile(delete=False, suffix=".log")
    handle.close()
    sys.stdout.flush()
    sys.stderr.flush()
    saved_out, saved_err = os.dup(1), os.dup(2)
    fd = os.open(handle.name, os.O_WRONLY)
    try:
        os.dup2(fd, 1)
        os.dup2(fd, 2)
        result = fn()
    finally:
        sys.stdout.flush()
        sys.stderr.flush()
        os.dup2(saved_out, 1)
        os.dup2(saved_err, 2)
        for d in (fd, saved_out, saved_err):
            os.close(d)
    with open(handle.name, encoding="utf-8", errors="replace") as fh:
        text = fh.read()
    try:
        os.remove(handle.name)
    except OSError:
        pass
    return result, text


NOISE = ("FreeCAD 1.", "(C) 2001", "FreeCAD is free", "Importing project files",
         "Postprocessing", "%)", "Time = ")


def recompute(doc, label):
    n, text = _capture(lambda: doc.recompute())
    bad = []
    for o in doc.Objects:
        st = o.State
        if "Invalid" in st or "Touched" in st:
            bad.append("%s[%s]:%s" % (o.Label, o.TypeId, ",".join(st)))
    lines = [ln.strip() for ln in text.splitlines() if ln.strip()]
    solver = [ln for ln in lines if ln.startswith("MbD:")]
    faults = [ln for ln in lines if not ln.startswith("MbD:")
              and not any(tok in ln for tok in NOISE)]
    out("  recompute(%s): %d objects; not Up-to-date: %s; console: %s%s" % (
        label, n, bad or "none", faults or "silent",
        "; assembly solver ran (%d MbD lines)" % len(solver) if solver else ""))
    return n, bad, faults


# --------------------------------------------------------------------------
# geometry helpers.  Feature shapes are body-local; Body.Shape carries the
# Body's own Placement (the assembly pose for T-Girt), so all measurement
# below reads Tip.Shape or transforms a loose body's feature by its Placement.

def tip_shape(body):
    return body.Tip.Shape


def slice_centre(shape, z0, z1):
    """Centre of the part of ``shape`` lying between z0 and z1 (body-local)."""
    box = Part.makeBox(2000, 2000, z1 - z0, App.Vector(-1000, -1000, z0))
    common = shape.common(box)
    if common.Volume < 1e-6:
        return None, 0.0
    return common.BoundBox.Center, common.Volume


def feature(body, prefix):
    for o in body.Group:
        if o.Label.startswith(prefix):
            return o
    raise RuntimeError("no feature %r* in %s" % (prefix, body.Label))


# --------------------------------------------------------------------------
# copying a joint-component body without dragging its frame and VarSet

def copy_body(doc, body, relabel):
    """Copy ``body`` with its features and Origin only, with_dependencies=False.

    External references (the frame it is placed on, the joint VarSet) are left
    pointing at the originals; links among the copied set are remapped by
    FreeCAD.  ``relabel(old_label) -> new_label`` names the copies.
    """
    members = [body] + list(body.Group) + [body.Origin] + list(body.Origin.OriginFeatures)
    copies = doc.copyObject(members, False)
    if not isinstance(copies, (list, tuple)):
        copies = [copies]
    # FreeCAD keeps labels unique by bumping the trailing digit run of the copy
    # (Tenon.MT.001 -> Tenon.MT.002), so match on type + label stem, in order.
    mapping = {}
    unused = list(copies)
    for src in members:
        hit = None
        for c in unused:
            if c.TypeId == src.TypeId and c.Label.rstrip("0123456789") == src.Label.rstrip("0123456789"):
                hit = c
                break
        if hit is None:
            raise RuntimeError("copy of %s (%s) not found among %s" % (
                src.Label, src.TypeId, [c.Label for c in copies]))
        unused.remove(hit)
        mapping[src.Name] = hit
    new_body = mapping[body.Name]
    for src in [body] + list(body.Group):
        mapping[src.Name].Label = relabel(src.Label)
    return new_body, mapping, copies


def with_serial(label, new_serial):
    """Replace the trailing digit run of a label (the serial) with new_serial."""
    stem = label.rstrip("0123456789")
    return stem + new_serial if stem != label else label + "." + new_serial


def serial_relabel(new_serial):
    return lambda label: with_serial(label, new_serial)


def prefix_relabel(pairs, serial=None):
    """Rename by descriptive prefix ((old, new), ...) and optionally reset the serial."""
    def f(label):
        for old, new in pairs:
            if label.startswith(old):
                label = new + label[len(old):]
                break
        return with_serial(label, serial) if serial else label
    return f


def fuse(target_body, operand, label):
    b = target_body.newObject("PartDesign::Boolean", "Boolean")
    b.addObjects([operand])
    b.Type = "Fuse"
    b.Refine = True
    b.Label = label
    return b


def repoint(body, old_tok, new_tok):
    """Rewrite every expression on the body and its features that names old_tok."""
    edits = []
    for o in [body] + list(body.Group):
        for path, expr in list(o.ExpressionEngine):
            if old_tok in expr:
                o.setExpression(path, expr.replace(old_tok, new_tok))
                edits.append("%s.%s: %s" % (o.Label, path, expr))
    return edits


def expressions_naming(body, tok):
    hits = []
    for o in [body] + list(body.Group):
        for path, expr in o.ExpressionEngine:
            if tok in expr:
                hits.append("%s.%s = %s" % (o.Label, path, expr))
    return hits


# ==========================================================================

def main():
    out("# Part H -- headless run")
    out()
    if not os.path.exists(SRC):
        raise SystemExit("missing %s" % SRC)
    _capture(lambda: None)  # flush FreeCAD's buffered startup banner out of the way
    doc = App.openDocument(SRC)
    doc.saveAs(OUT_H)
    out("Opened `%s`, working as `%s`." % (os.path.basename(SRC), os.path.basename(OUT_H)))
    out()

    girt = by_label(doc, "T-Girt")
    fa = by_label(doc, "F_Girt_A")
    fb = by_label(doc, "F_Girt_B")
    tdim = by_label(doc, "TDim_Girt")
    jvar = by_label(doc, "J-MT-001")
    tenonB = by_label(doc, "Tenon.MT.001")
    fuseB = by_label(doc, "Tenon.Add.MT.001")
    joint = [o for o in doc.Objects if o.TypeId == "App::FeaturePython"
             and hasattr(o, "Reference1")][0]

    girt_pose0 = App.Placement(girt.Placement)
    joint_refs0 = (str(joint.Reference1), str(joint.Reference2))
    L = tdim.LengthZ.Value
    WX, WY = tdim.WidthX.Value, tdim.WidthY.Value
    TL, HD = jvar.TenonLengthZ.Value, jvar.HousingDepth.Value
    TX, TY = jvar.TenonWidthX.Value, jvar.TenonWidthY.Value
    stick_vol = WX * WY * L
    adder_vol_expected = WX * WY * HD + TX * TY * TL
    out("Girt %s x %s x %s; tenon %s x %s x %s past a %s housing." % (
        inch(WX), inch(WY), inch(L), inch(TX), inch(TY), inch(TL), inch(HD)))
    out("Expected adder volume %.3f mm^3 (%.4f in^3); stick %.3f mm^3." % (
        adder_vol_expected, adder_vol_expected / IN ** 3, stick_vol))
    out()

    recompute(doc, "baseline")
    tip0 = tip_shape(girt)
    bb = tip0.BoundBox
    out("Baseline T-Girt tip (body-local): solids=%d volume=%.3f bbox z [%.3f, %.3f]" % (
        len(tip0.Solids), tip0.Volume, bb.ZMin, bb.ZMax))
    out("Baseline T-Girt Body.Shape bbox (assembly pose applied): z [%.3f, %.3f]" % (
        girt.Shape.BoundBox.ZMin, girt.Shape.BoundBox.ZMax))
    check("baseline: one solid, stick + one adder at end B",
          len(tip0.Solids) == 1 and near(tip0.Volume, stick_vol + adder_vol_expected, VOL_TOL)
          and near(bb.ZMin, 0) and near(bb.ZMax, L + TL + HD),
          "volume %.3f, z [%.3f, %.3f]" % (tip0.Volume, bb.ZMin, bb.ZMax))
    check("baseline: loose Tenon.MT.001 volume is the analytic adder volume",
          near(tenonB.Shape.Volume, adder_vol_expected, VOL_TOL),
          "%.3f mm^3" % tenonB.Shape.Volume)
    out()

    # ------------------------------------------------------------------ H0
    out("## H0 -- accessors on F_Girt_A")
    out()
    accessors = [
        ("WidthU", "<<TDim_Girt>>.WidthX", "Local X - Across timber face"),
        ("WidthV", "<<TDim_Girt>>.WidthY", "Local Y - Across timber end face"),
        ("DepthW", "<<TDim_Girt>>.LengthZ", "Local -Z - Depth of material behind end frame (stick length)"),
        ("HostLength", "<<TDim_Girt>>.LengthZ", "Length of stick"),
    ]
    for name, expr, tip in accessors:
        if not hasattr(fa, name):
            fa.addProperty("App::PropertyLength", name, "Frame", tip)
        fa.setExpression(name, expr)
    if not hasattr(fa, "Station"):
        fa.addProperty("App::PropertyLength", "Station", "Frame", "Z position of end frame (0 at end A)")
    fa.Station = 0.0
    fa.setExpression(".Placement.Base.z", "Station")
    if not hasattr(fa, "MateFrame"):
        fa.addProperty("App::PropertyString", "MateFrame", "Frame",
                       "Internal Name of the mated frame (unpaired)")
    recompute(doc, "H0")
    out()
    out("| Frame | WidthU | WidthV | DepthW | Station | HostLength | Position | Rotation (axis, angle) |")
    out("|---|---|---|---|---|---|---|---|")
    for fr in (fa, fb):
        r = fr.Placement.Rotation
        out("| `%s` | %s | %s | %s | %s | %s | (%.1f, %.1f, %.1f) | (%.3f, %.3f, %.3f), %.1f |" % (
            fr.Label, inch(fr.WidthU.Value), inch(fr.WidthV.Value), inch(fr.DepthW.Value),
            inch(fr.Station.Value), inch(fr.HostLength.Value),
            fr.Placement.Base.x, fr.Placement.Base.y, fr.Placement.Base.z,
            r.Axis.x, r.Axis.y, r.Axis.z, r.Angle * 180.0 / PI))
    out()
    check("H0: F_Girt_A accessors resolve 5 / 8 / 72 / 0 / 72 in",
          near(fa.WidthU.Value, WX) and near(fa.WidthV.Value, WY) and near(fa.DepthW.Value, L)
          and near(fa.Station.Value, 0) and near(fa.HostLength.Value, L),
          "%s / %s / %s / %s / %s" % (inch(fa.WidthU.Value), inch(fa.WidthV.Value),
                                      inch(fa.DepthW.Value), inch(fa.Station.Value),
                                      inch(fa.HostLength.Value)))
    q = fa.Placement.Rotation.Q
    check("H0: F_Girt_A still carries the declared 180-about-Y flip",
          near(abs(q[1]), 1.0, 1e-9) and near(fa.Placement.Base.z, 0),
          "Q = (%.3f, %.3f, %.3f, %.3f), z = %.3f" % (q[0], q[1], q[2], q[3], fa.Placement.Base.z))
    out()

    # ------------------------------------------------------------------ H1
    out("## H1 -- one tenon template, both ends, no edits")
    out()
    out("What `copyObject(Tenon.MT.001, with_dependencies=True)` drags along (probe, then removed):")
    dragged = doc.copyObject(tenonB, True, True)
    if not isinstance(dragged, (list, tuple)):
        dragged = [dragged]
    for d in sorted("%s (%s)" % (o.Label, o.TypeId) for o in dragged if not is_origin_part(o)):
        out("  - " + d)
    for o in list(dragged):
        try:
            doc.removeObject(o.Name)
        except Exception:  # noqa: BLE001
            pass
    recompute(doc, "after removing the dependency-copy probe")
    out()

    tenonA, mapping, copies = copy_body(doc, tenonB, serial_relabel("002"))
    out("Copied `%s` -> `%s`, %d objects, with_dependencies=False: %s" % (
        tenonB.Label, tenonA.Label, len(copies),
        [c.Label for c in copies if not is_origin_part(c)]))
    check("H1: copy's Tip, Origin and sketch supports are remapped into the copy",
          tenonA.Tip in copies and tenonA.Origin in copies
          and all(s.AttachmentSupport[0][0] in copies for s in tenonA.Group
                  if s.TypeId == "Sketcher::SketchObject"),
          "Tip=%s Origin=%s" % (tenonA.Tip.Label, tenonA.Origin.Name))
    ext = expressions_naming(tenonA, "<<F_Girt_B>>") + expressions_naming(tenonA, "<<J-MT-001>>")
    out("Copy's expressions still naming the originals (expected -- the point of the no-dependency copy):")
    for e in ext:
        out("  - " + e)
    tenonA.setExpression("Placement", "<<F_Girt_A>>.Placement")
    recompute(doc, "H1 copy bound to F_Girt_A")
    lb = tenonA.Shape.BoundBox
    check("H1: loose copy lands past end A, growing in -Z, centred on the section",
          near(lb.ZMax, 0) and near(lb.ZMin, -(TL + HD)) and near(lb.Center.x, 0) and near(lb.Center.y, 0),
          "bbox z [%.3f, %.3f], centre %s" % (lb.ZMin, lb.ZMax, fmt_vec(lb.Center)))
    check("H1: loose copy volume equals the end-B adder",
          near(tenonA.Shape.Volume, tenonB.Shape.Volume, VOL_TOL),
          "%.3f vs %.3f" % (tenonA.Shape.Volume, tenonB.Shape.Volume))
    fuseA = fuse(girt, tenonA, "Tenon.Add.MT.002")
    n, bad, faults = recompute(doc, "H1 fuse at end A")
    tip1 = tip_shape(girt)
    bb = tip1.BoundBox
    check("H1: T-Girt is one solid, stick + two adders, z from -(TenonLengthZ+HousingDepth) to L+(same)",
          len(tip1.Solids) == 1 and near(tip1.Volume, stick_vol + 2 * adder_vol_expected, VOL_TOL)
          and near(bb.ZMin, -(TL + HD)) and near(bb.ZMax, L + TL + HD),
          "solids=%d volume=%.3f (expected %.3f) z [%.3f, %.3f]" % (
              len(tip1.Solids), tip1.Volume, stick_vol + 2 * adder_vol_expected, bb.ZMin, bb.ZMax))
    cA, vA = slice_centre(tip1, -(TL + HD) + 5, -HD - 5)
    cB, vB = slice_centre(tip1, L + HD + 5, L + TL + HD - 5)
    check("H1: tenon cross-sections at both ends are centred and equal in volume",
          cA is not None and cB is not None and near(cA.x, 0) and near(cA.y, 0)
          and near(cB.x, 0) and near(cB.y, 0) and near(vA, vB, VOL_TOL),
          "end A %s vol %.3f; end B %s vol %.3f" % (fmt_vec(cA), vA, fmt_vec(cB), vB))
    check("H1: nothing left Touched/Invalid, console silent",
          not bad and not faults, "%s / %s" % (bad or "clean", faults or "silent"))
    h1_vol = tip1.Volume
    h1_bb = (bb.XMin, bb.XMax, bb.YMin, bb.YMax, bb.ZMin, bb.ZMax)
    out()

    # ------------------------------------------------------------------ H1b
    out("## H1b -- strict form: re-point <<F_Girt_B>> -> <<F_Girt_A>> on the copy")
    out()
    edits = repoint(tenonA, "<<F_Girt_B>>", "<<F_Girt_A>>")
    for e in edits:
        out("  - re-pointed " + e)
    n, bad, faults = recompute(doc, "H1b")
    tip1b = tip_shape(girt)
    bb = tip1b.BoundBox
    check("H1b: geometry unchanged after re-pointing (same volume, same bbox)",
          near(tip1b.Volume, h1_vol, VOL_TOL) and all(near(a, b) for a, b in zip(
              (bb.XMin, bb.XMax, bb.YMin, bb.YMax, bb.ZMin, bb.ZMax), h1_bb)),
          "volume %.3f; %d expressions edited; remaining refs to F_Girt_B: %s" % (
              tip1b.Volume, len(edits), expressions_naming(tenonA, "<<F_Girt_B>>") or "none"))
    check("H1b: nothing left Touched/Invalid, console silent",
          not bad and not faults, "%s / %s" % (bad or "clean", faults or "silent"))
    doc.saveCopy(OUT_H1)
    out("Saved H1 state as `%s`." % os.path.basename(OUT_H1))
    out()

    # ------------------------------------------------------------------ H2
    out("## H2 -- asymmetric adder at both ends")
    out()
    fuseB.Suppressed = True
    fuseA.Suppressed = True
    recompute(doc, "H2: symmetric tenons suppressed")
    tipS = tip_shape(girt)
    check("H2: with both symmetric fuses suppressed the girt is the bare stick",
          len(tipS.Solids) == 1 and near(tipS.Volume, stick_vol, VOL_TOL),
          "volume %.3f (stick %.3f)" % (tipS.Volume, stick_vol))

    OFF = App.Vector(IN, IN / 2, 0)
    offB, m2, c2 = copy_body(doc, tenonB, prefix_relabel(
        (("Tenon", "TenonOff"), ("Shoulder", "ShoulderOff")), serial="001"))
    sk = feature(offB, "TenonOff.SKT")
    sk.AttachmentOffset = App.Placement(OFF, App.Rotation())
    recompute(doc, "H2: TenonOff.MT.001 at end B")
    padB = feature(offB, "TenonOff.Pad")
    cb_local = padB.Shape.BoundBox.Center
    cb_girt = offB.Placement.multVec(cb_local)
    out("Loose `%s` tenon prism centre: body-local %s -> girt-local %s" % (
        offB.Label, fmt_vec(cb_local), fmt_vec(cb_girt)))
    check("H2: the offset really is (+1 in, +1/2 in) in the adder's own frame",
          near(cb_local.x, OFF.x) and near(cb_local.y, OFF.y), fmt_vec(cb_local))

    offA, m3, c3 = copy_body(doc, offB, serial_relabel("002"))
    offA.setExpression("Placement", "<<F_Girt_A>>.Placement")
    repoint(offA, "<<F_Girt_B>>", "<<F_Girt_A>>")
    recompute(doc, "H2: TenonOff.MT.002 at end A")
    fuseOffB = fuse(girt, offB, "TenonOff.Add.MT.001")
    fuseOffA = fuse(girt, offA, "TenonOff.Add.MT.002")
    n, bad, faults = recompute(doc, "H2: both asymmetric adders fused")

    def measure_ends(tag):
        tip = tip_shape(girt)
        cA_, vA_ = slice_centre(tip, -(TL + HD) + 5, -HD - 5)
        cB_, vB_ = slice_centre(tip, L + HD + 5, L + TL + HD - 5)
        fxA, fyA = face_of(cA_.x, cA_.y) if cA_ else ("?", "?")
        fxB, fyB = face_of(cB_.x, cB_.y) if cB_ else ("?", "?")
        out("| %s | %s | %s | %s / %s | %s / %s | %d | %.3f |" % (
            tag, fmt_vec(cB_), fmt_vec(cA_), fxB, fyB, fxA, fyA, len(tip.Solids), tip.Volume))
        return tip, cA_, cB_

    out()
    out("| F_Girt_A flip | end B tenon centre (girt-local) | end A tenon centre (girt-local) "
        "| end B favours | end A favours | solids | volume |")
    out("|---|---|---|---|---|---|---|")
    tipY, cA_Y, cB_Y = measure_ends("180 about local Y (declared)")
    check("H2: one solid, stick + two adders",
          len(tipY.Solids) == 1 and near(tipY.Volume, stick_vol + 2 * adder_vol_expected, VOL_TOL),
          "solids=%d volume=%.3f" % (len(tipY.Solids), tipY.Volume))
    check("H2 (Y-flip): end B favours +X/+Y, end A favours -X/+Y -- opposite X faces, same Y face",
          cA_Y is not None and cB_Y is not None
          and near(cB_Y.x, OFF.x) and near(cB_Y.y, OFF.y)
          and near(cA_Y.x, -OFF.x) and near(cA_Y.y, OFF.y),
          "B %s; A %s" % (fmt_vec(cB_Y), fmt_vec(cA_Y)))
    check("H2 (Y-flip): nothing left Touched/Invalid, console silent",
          not bad and not faults, "%s / %s" % (bad or "clean", faults or "silent"))

    # X-flip variant
    yflip = App.Rotation(fa.Placement.Rotation)
    fa.Placement = App.Placement(fa.Placement.Base, App.Rotation(App.Vector(1, 0, 0), 180))
    n, bad, faults = recompute(doc, "H2: F_Girt_A re-placed to 180 about local X")
    tipX, cA_X, cB_X = measure_ends("180 about local X (alternative)")
    check("H2 (X-flip): end A favours +X/-Y -- same X face, opposite Y face; F_Girt_A accessors unchanged",
          cA_X is not None and near(cA_X.x, OFF.x) and near(cA_X.y, -OFF.y)
          and near(fa.WidthU.Value, WX) and near(fa.WidthV.Value, WY),
          "A %s; WidthU %s WidthV %s" % (fmt_vec(cA_X), inch(fa.WidthU.Value), inch(fa.WidthV.Value)))
    check("H2 (X-flip): one solid, nothing Touched/Invalid, console silent",
          len(tipX.Solids) == 1 and not bad and not faults,
          "solids=%d / %s / %s" % (len(tipX.Solids), bad or "clean", faults or "silent"))
    doc.saveCopy(OUT_XFLIP)
    out()
    out("Saved the X-flip variant as `%s`." % os.path.basename(OUT_XFLIP))
    fa.Placement = App.Placement(fa.Placement.Base, yflip)
    recompute(doc, "H2: Y-flip restored")
    out()
    out("| F_Girt_A flip | end B tenon centre (girt-local) | end A tenon centre (girt-local) "
        "| end B favours | end A favours | solids | volume |")
    out("|---|---|---|---|---|---|---|")
    tipR, cA_R, cB_R = measure_ends("180 about local Y (restored)")
    check("H2: restoring the Y-flip reproduces the first measurement",
          cA_R is not None and near(cA_R.x, cA_Y.x) and near(cA_R.y, cA_Y.y), fmt_vec(cA_R))
    check("H2: assembly joint references and T-Girt's seated pose untouched throughout",
          (str(joint.Reference1), str(joint.Reference2)) == joint_refs0
          and girt.Placement.isSame(girt_pose0, 1e-9),
          "refs %s; pose %s" % (joint_refs0, girt.Placement))
    out()

    # ------------------------------------------------------------------ H3
    out("## H3 -- native mirror probe")
    out()
    tpl, m4, c4 = copy_body(doc, offB, prefix_relabel(
        (("TenonOff", "TenonOffTpl"), ("ShoulderOff", "ShoulderOffTpl")), serial="001"))
    tpl.setExpression("Placement", None)
    tpl.Placement = App.Placement()
    recompute(doc, "H3: unplaced template copy at origin")
    tb = tpl.Shape.BoundBox
    out("Template copy bbox z [%.3f, %.3f] (adder grows +Z from its origin)." % (tb.ZMin, tb.ZMax))

    mir = doc.addObject("Part::Mirroring", "TenonOffMirror")
    mir.Label = "TenonOff.Mirror.MT.001"
    mir.Source = tpl
    mir.Normal = App.Vector(0, 0, 1)
    mir.Base = App.Vector(0, 0, 0)
    n, bad, faults = recompute(doc, "H3: Part::Mirroring about the frame's XY plane")
    mb = mir.Shape.BoundBox
    cm, vm = slice_centre(mir.Shape, -(TL + HD) + 5, -HD - 5)
    check("H3: mirrored adder grows -Z with the tenon still at (+1, +1/2) -- a mirror keeps the faces",
          near(mb.ZMax, 0) and near(mb.ZMin, -(TL + HD)) and cm is not None
          and near(cm.x, OFF.x) and near(cm.y, OFF.y) and len(mir.Shape.Solids) == 1,
          "bbox z [%.3f, %.3f]; tenon centre %s; solids %d" % (
              mb.ZMin, mb.ZMax, fmt_vec(cm), len(mir.Shape.Solids)))

    fuseOffA.Suppressed = True
    recompute(doc, "H3: Y-flip adder at end A suppressed")

    # route (a): the Part::Mirroring directly as a PartDesign::Boolean operand
    route_a = None
    fuseMirA = None
    try:
        fuseMirA = fuse(girt, mir, "TenonMir.Add.MT.001a")
        n, bad, faults = recompute(doc, "H3 route (a): Part::Mirroring as Boolean operand")
        tipMa = tip_shape(girt)
        cA_Ma, _ = slice_centre(tipMa, -(TL + HD) + 5, -HD - 5)
        route_a = (len(tipMa.Solids), tipMa.Volume, cA_Ma, list(fuseMirA.State), bad, faults)
        out("Route (a): Boolean state %s; solids %d; volume %.3f; end-A tenon centre %s" % (
            fuseMirA.State, len(tipMa.Solids), tipMa.Volume, fmt_vec(cA_Ma)))
    except Exception as exc:  # noqa: BLE001
        out("Route (a) raised: %r" % (exc,))
    if fuseMirA is not None:
        fuseMirA.Suppressed = True
    recompute(doc, "H3: route (a) suppressed")

    # route (b): a Body whose BaseFeature is the mirroring.  A second mirror
    # object, because route (a)'s Boolean claimed the first into its Group
    # (inside T-Girt, inside the Assembly), which a root-level Body may not link.
    # Route (a)'s Boolean also claimed the mirror's *source* body into T-Girt's
    # scope, so route (b) gets its own template copy as well.
    tpl2, m5, c5 = copy_body(doc, tpl, serial_relabel("002"))
    recompute(doc, "H3: second template copy for route (b)")
    mir2 = doc.addObject("Part::Mirroring", "TenonOffMirror2")
    mir2.Label = "TenonOff.Mirror.MT.002"
    mir2.Source = tpl2
    mir2.Normal = App.Vector(0, 0, 1)
    mir2.Base = App.Vector(0, 0, 0)
    wrap = doc.addObject("PartDesign::Body", "TenonMirBody")
    wrap.Label = "TenonMir.MT.001"
    fuseMirB = None
    try:
        wrap.BaseFeature = mir2
        recompute(doc, "H3 route (b): Body with BaseFeature = mirroring")
        wb = wrap.Shape.BoundBox
        out("Wrapper body bbox z [%.3f, %.3f], solids %d" % (wb.ZMin, wb.ZMax, len(wrap.Shape.Solids)))
        fuseMirB = fuse(girt, wrap, "TenonMir.Add.MT.001b")
        n, bad, faults = recompute(doc, "H3 route (b): wrapper Body as Boolean operand")
        tipMb = tip_shape(girt)
        cA_Mb, _ = slice_centre(tipMb, -(TL + HD) + 5, -HD - 5)
        out("Route (b): Boolean state %s; solids %d; volume %.3f; end-A tenon centre %s" % (
            fuseMirB.State, len(tipMb.Solids), tipMb.Volume, fmt_vec(cA_Mb)))
        check("H3 route (b): one solid, stick + two adders, end A favours +X/+Y like end B",
              len(tipMb.Solids) == 1 and near(tipMb.Volume, stick_vol + 2 * adder_vol_expected, VOL_TOL)
              and cA_Mb is not None and near(cA_Mb.x, OFF.x) and near(cA_Mb.y, OFF.y)
              and not bad and not faults,
              "solids=%d volume=%.3f centre %s; %s / %s" % (
                  len(tipMb.Solids), tipMb.Volume, fmt_vec(cA_Mb), bad or "clean", faults or "silent"))
    except Exception as exc:  # noqa: BLE001
        out("Route (b) raised: %r" % (exc,))
    if fuseMirB is not None:
        fuseMirB.Suppressed = True
    if route_a is not None:
        check("H3 route (a): Part::Mirroring accepted directly as a Boolean operand",
              route_a[0] == 1 and near(route_a[1], stick_vol + 2 * adder_vol_expected, VOL_TOL)
              and route_a[2] is not None and near(route_a[2].x, OFF.x)
              and not route_a[4] and not route_a[5],
              "solids=%d volume=%.3f state=%s bad=%s console=%s" % (
                  route_a[0], route_a[1], route_a[3], route_a[4] or "clean", route_a[5] or "silent"))

    # route (c): the form an apply tool would use -- mirror the unplaced copy
    # across its own local X (the YZ plane), then bind the mirror's Placement to
    # the end-A frame exactly as any component is placed.  Under the Y-flip,
    # F_A o mirrorX == mirror about the end plane, so the faces should match end B.
    fuseMirC = None
    try:
        tpl3, m6, c6 = copy_body(doc, tpl, serial_relabel("003"))
        recompute(doc, "H3: third template copy for route (c)")
        mir3 = doc.addObject("Part::Mirroring", "TenonOffMirror3")
        mir3.Label = "TenonOff.MirrorX.MT.003"
        mir3.Source = tpl3
        mir3.Normal = App.Vector(1, 0, 0)
        mir3.Base = App.Vector(0, 0, 0)
        mir3.setExpression("Placement", "<<F_Girt_A>>.Placement")
        recompute(doc, "H3 route (c): mirror across local X, placed on F_Girt_A")
        m3b = mir3.Shape.BoundBox
        cm3, _ = slice_centre(mir3.Shape, -(TL + HD) + 5, -HD - 5)
        out("Route (c) loose mirrored copy: bbox z [%.3f, %.3f]; tenon centre %s" % (
            m3b.ZMin, m3b.ZMax, fmt_vec(cm3)))
        fuseMirC = fuse(girt, mir3, "TenonMir.Add.MT.001c")
        n, bad, faults = recompute(doc, "H3 route (c): fused")
        tipMc = tip_shape(girt)
        cA_Mc, _ = slice_centre(tipMc, -(TL + HD) + 5, -HD - 5)
        check("H3 route (c): mirror across frame-local X, placed by <<F_Girt_A>>.Placement -- one solid, end A favours +X/+Y",
              len(tipMc.Solids) == 1 and near(tipMc.Volume, stick_vol + 2 * adder_vol_expected, VOL_TOL)
              and cA_Mc is not None and near(cA_Mc.x, OFF.x) and near(cA_Mc.y, OFF.y)
              and not bad and not faults,
              "solids=%d volume=%.3f centre %s; %s / %s" % (
                  len(tipMc.Solids), tipMc.Volume, fmt_vec(cA_Mc), bad or "clean", faults or "silent"))
    except Exception as exc:  # noqa: BLE001
        out("Route (c) raised: %r" % (exc,))
    if fuseMirC is not None:
        fuseMirC.Suppressed = True

    # Final state, per Adam's H2 decision (GUI replay, 2026-09-18): the end-A
    # component keeps its timber-local x,y offsets, i.e. the mirrored form
    # (route c) is what is wanted; the rotated end-A adder stays but suppressed.
    fuseOffA.Suppressed = True
    if fuseMirC is not None:
        fuseMirC.Suppressed = False
    n, bad, faults = recompute(doc, "final: mirrored end-A adder active (the decided convention)")
    tipF = tip_shape(girt)
    cA_F, _ = slice_centre(tipF, -(TL + HD) + 5, -HD - 5)
    cB_F, _ = slice_centre(tipF, L + HD + 5, L + TL + HD - 5)
    check("final: one solid, stick + two asymmetric adders, both tenons at (+1, +1/2) girt-local",
          len(tipF.Solids) == 1 and near(tipF.Volume, stick_vol + 2 * adder_vol_expected, VOL_TOL)
          and not bad and cA_F is not None and cB_F is not None
          and near(cA_F.x, OFF.x) and near(cA_F.y, OFF.y) and near(cB_F.x, OFF.x) and near(cB_F.y, OFF.y),
          "solids=%d volume=%.3f; A %s; B %s; %s" % (
              len(tipF.Solids), tipF.Volume, fmt_vec(cA_F), fmt_vec(cB_F), bad or "clean"))
    if cA_F is not None and cB_F is not None:
        wA, wB = girt.Placement.multVec(cA_F), girt.Placement.multVec(cB_F)
        out("World-frame tenon centres (assembly pose): end A %s; end B %s" % (fmt_vec(wA), fmt_vec(wB)))
        check("final: in world coordinates the two tenons share X and Z and differ only along the girt (world Y)",
              near(wA.x, wB.x, 1e-6) and near(wA.z, wB.z, 1e-6) and abs(wA.y - wB.y) > L,
              "A (%.3f, %.3f, %.3f) B (%.3f, %.3f, %.3f)" % (wA.x, wA.y, wA.z, wB.x, wB.y, wB.z))
    doc.save()
    out()
    out("Saved `%s`." % os.path.basename(OUT_H))
    out()
    out("## Checks")
    out()
    out("| Check | Result | Observed |")
    out("|---|---|---|")
    for name, status, obs in CHECKS:
        out("| %s | **%s** | %s |" % (name, status, obs.replace("|", "/")))
    fails = [c for c in CHECKS if c[1] == "FAIL"]
    out()
    out("**%d checks, %d failed.**" % (len(CHECKS), len(fails)))
    with open(RESULTS_MD, "w", encoding="utf-8") as fh:
        fh.write("\n".join(LINES) + "\n")
    if App.GuiUp:
        import FreeCADGui
        FreeCADGui.SendMsgToActiveView("ViewFit")
    return len(fails)


_rc = main()
sys.stdout.flush()
if not App.GuiUp:
    sys.exit(_rc)
