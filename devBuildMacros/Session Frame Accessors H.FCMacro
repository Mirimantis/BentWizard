# Macro Begin: C:\Users\Adam\Documents\Projects\BentWizard\devBuildMacros\Session Frame Accessors H.FCMacro +++++++++++++++++++++++++++++++++++++++++++++++++
import FreeCAD
import PartDesign

# Gui.runCommand('Std_DlgMacroRecord',0)
# Gui.Selection.clearSelection()
# Gui.Selection.addSelection('Frame_Accessors_Part_G','Assembly','Body001.Boolean001.')
# Gui.Selection.clearSelection()
# Gui.Selection.addSelection('Frame_Accessors_Part_G','Assembly','Body001.Boolean001.Body003.')
# Gui.runCommand('Std_Copy',0)
# Gui.Selection.addSelection('Frame_Accessors_Part_G','Assembly','Body001.Boolean001.Body003.Origin011.')
# Gui.Selection.addSelection('Frame_Accessors_Part_G','Assembly','Body001.Boolean001.Body003.Pad004.')
# Gui.Selection.addSelection('Frame_Accessors_Part_G','Assembly','Body001.Boolean001.Body003.Pad004.Sketch004.')
# Gui.Selection.addSelection('Frame_Accessors_Part_G','Assembly','Body001.Boolean001.Body003.Pad005.')
# Gui.Selection.addSelection('Frame_Accessors_Part_G','Assembly','Body001.Boolean001.Body003.Pad005.Sketch005.')
# Gui.runCommand('Std_Copy',0)
# Gui.Selection.clearSelection()
# Gui.runCommand('Std_Paste',0)
# Gui.Selection.addSelection('Frame_Accessors_Part_G','Body004')
App.activeDocument().recompute(None,True,True)
# Gui.runCommand('Std_Undo',0)
# Gui.Selection.addSelection('Frame_Accessors_Part_G','Assembly')
# Gui.runCommand('Std_Redo',0)
# Gui.Selection.clearSelection()
# Gui.Selection.addSelection('Frame_Accessors_Part_G','Body004')
# Gui.Selection.clearSelection()
# Gui.Selection.addSelection('Frame_Accessors_Part_G','Assembly','Body001.')
# Gui.activateWorkbench('PartDesignWorkbench')
# Gui.ActiveDocument.ActiveView.setActiveObject('part',App.getDocument('Frame_Accessors_Part_G').getObject('Assembly'))
# Gui.ActiveDocument.ActiveView.setActiveObject('pdbody',App.getDocument('Frame_Accessors_Part_G').getObject('Body001'))
# Gui.Selection.clearSelection()
# Gui.Selection.addSelection('Frame_Accessors_Part_G','Assembly','Body001.')
### Begin command PartDesign_Boolean
App.getDocument('Frame_Accessors_Part_G').getObject('Body001').newObject('PartDesign::Boolean','Boolean002')
# App.getDocument('Frame_Accessors_Part_G').getObject('Boolean002').ViewObject.ShapeAppearance=getattr(App.getDocument('Frame_Accessors_Part_G').getObject('Boolean001').getLinkedObject(True).ViewObject,'ShapeAppearance',App.getDocument('Frame_Accessors_Part_G').getObject('Boolean002').ViewObject.ShapeAppearance)
# App.getDocument('Frame_Accessors_Part_G').getObject('Boolean002').ViewObject.LineColor=getattr(App.getDocument('Frame_Accessors_Part_G').getObject('Boolean001').getLinkedObject(True).ViewObject,'LineColor',App.getDocument('Frame_Accessors_Part_G').getObject('Boolean002').ViewObject.LineColor)
# App.getDocument('Frame_Accessors_Part_G').getObject('Boolean002').ViewObject.PointColor=getattr(App.getDocument('Frame_Accessors_Part_G').getObject('Boolean001').getLinkedObject(True).ViewObject,'PointColor',App.getDocument('Frame_Accessors_Part_G').getObject('Boolean002').ViewObject.PointColor)
# App.getDocument('Frame_Accessors_Part_G').getObject('Boolean002').ViewObject.Transparency=getattr(App.getDocument('Frame_Accessors_Part_G').getObject('Boolean001').getLinkedObject(True).ViewObject,'Transparency',App.getDocument('Frame_Accessors_Part_G').getObject('Boolean002').ViewObject.Transparency)
# App.getDocument('Frame_Accessors_Part_G').getObject('Boolean002').ViewObject.DisplayMode=getattr(App.getDocument('Frame_Accessors_Part_G').getObject('Boolean001').getLinkedObject(True).ViewObject,'DisplayMode',App.getDocument('Frame_Accessors_Part_G').getObject('Boolean002').ViewObject.DisplayMode)
# Gui.getDocument('Frame_Accessors_Part_G').setEdit(App.getDocument('Frame_Accessors_Part_G').getObject('Assembly'), 0, 'Body001.Boolean002.')
# Gui.Selection.clearSelection()
### End command PartDesign_Boolean
# Gui.Selection.clearSelection()
# Gui.activeDocument().resetEdit()
# Gui.Selection.addSelection('Frame_Accessors_Part_G','Body004')
### Begin command PartDesign_Boolean
App.getDocument('Frame_Accessors_Part_G').getObject('Body001').newObject('PartDesign::Boolean','Boolean002')
App.getDocument('Frame_Accessors_Part_G').getObject('Boolean002').addObjects([App.getDocument('Frame_Accessors_Part_G').getObject('Body004'),])
App.ActiveDocument.recompute()
# App.getDocument('Frame_Accessors_Part_G').getObject('Boolean002').ViewObject.ShapeAppearance=getattr(App.getDocument('Frame_Accessors_Part_G').getObject('Boolean001').getLinkedObject(True).ViewObject,'ShapeAppearance',App.getDocument('Frame_Accessors_Part_G').getObject('Boolean002').ViewObject.ShapeAppearance)
# App.getDocument('Frame_Accessors_Part_G').getObject('Boolean002').ViewObject.LineColor=getattr(App.getDocument('Frame_Accessors_Part_G').getObject('Boolean001').getLinkedObject(True).ViewObject,'LineColor',App.getDocument('Frame_Accessors_Part_G').getObject('Boolean002').ViewObject.LineColor)
# App.getDocument('Frame_Accessors_Part_G').getObject('Boolean002').ViewObject.PointColor=getattr(App.getDocument('Frame_Accessors_Part_G').getObject('Boolean001').getLinkedObject(True).ViewObject,'PointColor',App.getDocument('Frame_Accessors_Part_G').getObject('Boolean002').ViewObject.PointColor)
# App.getDocument('Frame_Accessors_Part_G').getObject('Boolean002').ViewObject.Transparency=getattr(App.getDocument('Frame_Accessors_Part_G').getObject('Boolean001').getLinkedObject(True).ViewObject,'Transparency',App.getDocument('Frame_Accessors_Part_G').getObject('Boolean002').ViewObject.Transparency)
# App.getDocument('Frame_Accessors_Part_G').getObject('Boolean002').ViewObject.DisplayMode=getattr(App.getDocument('Frame_Accessors_Part_G').getObject('Boolean001').getLinkedObject(True).ViewObject,'DisplayMode',App.getDocument('Frame_Accessors_Part_G').getObject('Boolean002').ViewObject.DisplayMode)
# Gui.getDocument('Frame_Accessors_Part_G').setEdit(App.getDocument('Frame_Accessors_Part_G').getObject('Assembly'), 0, 'Body001.Boolean002.')
# Gui.Selection.clearSelection()
### End command PartDesign_Boolean
# Gui.Selection.clearSelection()
App.getDocument('Frame_Accessors_Part_G').getObject('Boolean002').setObjects( [App.getDocument('Frame_Accessors_Part_G').getObject('Body004'),])
App.getDocument('Frame_Accessors_Part_G').getObject('Boolean002').Type = 0
App.ActiveDocument.recompute()
# Gui.activeDocument().resetEdit()
### Begin command Std_Save
# Gui.SendMsgToActiveView("Save")
App.getDocument("Frame_Accessors_Part_G").save()
### End command Std_Save
### Begin command Std_Save
# Gui.SendMsgToActiveView("Save")
App.getDocument("Frame_Accessors_Part_G").save()
### End command Std_Save
FreeCAD.open(u"C:/Users/Adam/Documents/Projects/BentWizard/scratch/Frame Accessors Part H.FCStd")
# App.setActiveDocument("Frame_Accessors_Part_H")
# App.ActiveDocument=App.getDocument("Frame_Accessors_Part_H")
# Gui.ActiveDocument=Gui.getDocument("Frame_Accessors_Part_H")
# Gui.Selection.addSelection('Frame_Accessors_Part_H','TenonOffMirror2')
# Gui.Selection.addSelection('Frame_Accessors_Part_H','Assembly','Body.')
# Gui.Selection.addSelection('Frame_Accessors_Part_H','Assembly','Body001.')
# Gui.Selection.clearSelection()
# Gui.Selection.addSelection('Frame_Accessors_Part_H','Assembly','Body001.')
# Gui.Selection.addSelection('Frame_Accessors_Part_H','Assembly','Body.')
# Gui.runCommand('Std_ToggleTransparency',0)
# Gui.Selection.clearSelection()
# App.setActiveDocument("Frame_Accessors_Part_G")
# App.ActiveDocument=App.getDocument("Frame_Accessors_Part_G")
# Gui.ActiveDocument=Gui.getDocument("Frame_Accessors_Part_G")
# Macro End: C:\Users\Adam\Documents\Projects\BentWizard\devBuildMacros\Session Frame Accessors H.FCMacro +++++++++++++++++++++++++++++++++++++++++++++++++
