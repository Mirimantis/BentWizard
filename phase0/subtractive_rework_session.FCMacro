# Macro Begin: C:\Users\Adam\Documents\Projects\BentWizard\subtractive_rework_session.FCMacro +++++++++++++++++++++++++++++++++++++++++++++++++
import FreeCAD
import PartDesignGui
import Sketcher
import PartDesign

# Gui.runCommand('Std_DlgMacroRecord',0)
# Gui.Selection.clearSelection()
# Gui.Selection.addSelection('Joint_HouseMT_session_4','Body002','Pad004.Face10',1245.96,152.4,330.011)
# Gui.Selection.clearSelection()
# Gui.Selection.addSelection('Joint_HouseMT_session_4','Body002','Pad004.Face1',1219.2,81.8062,584.071)
# Gui.Selection.clearSelection()
# Gui.Selection.addSelection('Joint_HouseMT_session_4','Body002')
# Gui.ActiveDocument.ActiveView.setActiveObject('pdbody',App.getDocument('Joint_HouseMT_session_4').getObject('Body002'))
# Gui.Selection.clearSelection()
# Gui.Selection.addSelection('Joint_HouseMT_session_4','Body002','Pocket003.')
### Begin command Std_Delete
App.getDocument('Joint_HouseMT_session_4').getObject('Body002').removeObject(App.getDocument('Joint_HouseMT_session_4').getObject('Pocket003'))
App.getDocument('Joint_HouseMT_session_4').removeObject('Pocket003')
App.getDocument('Joint_HouseMT_session_4').recompute()
### End command Std_Delete
# Gui.Selection.clearSelection()
# Gui.Selection.addSelection('Joint_HouseMT_session_4','Body002','Pocket002.')
### Begin command Std_Delete
App.getDocument('Joint_HouseMT_session_4').getObject('Body002').removeObject(App.getDocument('Joint_HouseMT_session_4').getObject('Pocket002'))
App.getDocument('Joint_HouseMT_session_4').removeObject('Pocket002')
App.getDocument('Joint_HouseMT_session_4').recompute()
### End command Std_Delete
# Gui.Selection.clearSelection()
# Gui.Selection.addSelection('Joint_HouseMT_session_4','Body002','DatumPlane001.')
### Begin command Std_Delete
App.getDocument('Joint_HouseMT_session_4').removeObject('DatumPlane001')
App.getDocument('Joint_HouseMT_session_4').recompute()
### End command Std_Delete
# Gui.Selection.addSelection('Joint_HouseMT_session_4','Body002','Pad003.')
# Gui.Selection.clearSelection()
# Gui.Selection.addSelection('Joint_HouseMT_session_4','VarSet006')
### Begin command Std_Delete
App.getDocument('Joint_HouseMT_session_4').removeObject('VarSet006')
App.getDocument('Joint_HouseMT_session_4').recompute()
### End command Std_Delete
# Gui.Selection.addSelection('Joint_HouseMT_session_4','VarSet005')
### Begin command Std_Delete
App.getDocument('Joint_HouseMT_session_4').removeObject('VarSet005')
App.getDocument('Joint_HouseMT_session_4').recompute()
### End command Std_Delete
# Gui.Selection.addSelection('Joint_HouseMT_session_4','VarSet004')
# Gui.Selection.clearSelection()
# Gui.Selection.addSelection('Joint_HouseMT_session_4','Body002','Sketch006.')
### Begin command Std_Delete
App.getDocument('Joint_HouseMT_session_4').removeObject('Sketch006')
App.getDocument('Joint_HouseMT_session_4').recompute()
### End command Std_Delete
# Gui.Selection.addSelection('Joint_HouseMT_session_4','Body002','Pad003.')
# Gui.Selection.clearSelection()
# Gui.Selection.addSelection('Joint_HouseMT_session_4','Body002','Sketch007.')
### Begin command Std_Delete
App.getDocument('Joint_HouseMT_session_4').removeObject('Sketch007')
App.getDocument('Joint_HouseMT_session_4').recompute()
### End command Std_Delete
# Gui.Selection.addSelection('Joint_HouseMT_session_4','Body002','Pad003.')
# Gui.Selection.clearSelection()
# Gui.Selection.addSelection('Joint_HouseMT_session_4','Body001','Pad002.')
# Gui.runCommand('Std_Delete',0)
### Begin command Std_Delete
App.getDocument('Joint_HouseMT_session_4').getObject('Body001').removeObject(App.getDocument('Joint_HouseMT_session_4').getObject('Pad002'))
App.getDocument('Joint_HouseMT_session_4').removeObject('Pad002')
App.getDocument('Joint_HouseMT_session_4').recompute()
### End command Std_Delete
# Gui.Selection.clearSelection()
# Gui.Selection.addSelection('Joint_HouseMT_session_4','Body001','Sketch002.')
# Gui.Selection.clearSelection()
# ActiveSketch = App.getDocument('Joint_HouseMT_session_4').getObject('Sketch002')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Joint_HouseMT_session_4').getObject('Body001'), 'Sketch002.'))
# if ActiveSketch.ViewObject.ShowSupport:
#   tv.show([ref[0] for ref in ActiveSketch.AttachmentSupport if not (ref[0].isDerivedFrom("App::Plane") or ref[0].isDerivedFrom("App::LocalCoordinateSystem"))])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
App.getDocument('Joint_HouseMT_session_4').getObject('Sketch002').setVisibility([0,1,2,3,4,5,6,7,8,9,10,11], True)
# ActiveSketch = App.getDocument('Joint_HouseMT_session_4').getObject('Sketch002')
# if ActiveSketch.ViewObject.RestoreCamera:
#   ActiveSketch.ViewObject.TempoVis.saveCamera()
#   if ActiveSketch.ViewObject.ForceOrtho:
#     ActiveSketch.ViewObject.Document.ActiveView.setCameraType('Orthographic')
# 
# Gui.runCommand('Sketcher_CompCreateRectangles',0)
ActiveSketch = App.getDocument('Joint_HouseMT_session_4').getObject('Sketch002')

lastGeoId = len(ActiveSketch.Geometry)

geoList = []
geoList.append(Part.LineSegment(App.Vector(0.000000, 0.000000, 0.000000),App.Vector(367.532751, 0.000000, 0.000000)))
geoList.append(Part.LineSegment(App.Vector(367.532751, 0.000000, 0.000000),App.Vector(367.532751, 308.912109, 0.000000)))
geoList.append(Part.LineSegment(App.Vector(367.532751, 308.912109, 0.000000),App.Vector(0.000000, 308.912109, 0.000000)))
geoList.append(Part.LineSegment(App.Vector(0.000000, 308.912109, 0.000000),App.Vector(0.000000, 0.000000, 0.000000)))
App.getDocument('Joint_HouseMT_session_4').getObject('Sketch002').addGeometry(geoList,False)
del geoList

constraintList = []
constraintList.append(Sketcher.Constraint('Coincident', 4, 2, 5, 1))
constraintList.append(Sketcher.Constraint('Coincident', 5, 2, 6, 1))
constraintList.append(Sketcher.Constraint('Coincident', 6, 2, 7, 1))
constraintList.append(Sketcher.Constraint('Coincident', 7, 2, 4, 1))
constraintList.append(Sketcher.Constraint('Horizontal', 4))
constraintList.append(Sketcher.Constraint('Horizontal', 6))
constraintList.append(Sketcher.Constraint('Vertical', 5))
constraintList.append(Sketcher.Constraint('Vertical', 7))
App.getDocument('Joint_HouseMT_session_4').getObject('Sketch002').addConstraint(constraintList)
del constraintList

App.getDocument('Joint_HouseMT_session_4').getObject('Sketch002').addConstraint(Sketcher.Constraint('Coincident', 4, 1, -1, 1))


# Gui.Selection.addSelection('Joint_HouseMT_session_4','Body001','Sketch002.Vertex14',609.6,308.912,0.014,False)
# Gui.Selection.addSelection('Joint_HouseMT_session_4','Body001','Sketch002.Vertex12',977.133,308.912,0.014,False)
App.getDocument('Joint_HouseMT_session_4').getObject('Sketch002').moveGeometries([(6, 2), (5, 2)], App.Vector(14.7463, -10.6905, 0), True)
### Begin command Sketcher_CompDimensionTools
App.getDocument('Joint_HouseMT_session_4').getObject('Sketch002').addConstraint(Sketcher.Constraint('Distance',6,2,5,2,382.279051)) 
### End command Sketcher_CompDimensionTools
# Gui.Selection.clearSelection()
App.getDocument('Joint_HouseMT_session_4').getObject('Sketch002').addConstraint(Sketcher.Constraint('DistanceX',6,2,5,2,382.279051)) 
App.getDocument('Joint_HouseMT_session_4').Sketch002.setExpression('Constraints[21]', u'<<BeamDims>>.Width')
# Gui.Selection.addSelection('Joint_HouseMT_session_4','Body001','Sketch002.Vertex12',812.8,298.222,0.014,False)
# Gui.Selection.addSelection('Joint_HouseMT_session_4','Body001','Sketch002.Vertex10',812.8,0,0.014,False)
### Begin command Sketcher_Dimension
App.getDocument('Joint_HouseMT_session_4').getObject('Sketch002').addConstraint(Sketcher.Constraint('Distance',5,2,4,2,298.221609)) 
### End command Sketcher_Dimension
# Gui.Selection.clearSelection()
App.getDocument('Joint_HouseMT_session_4').getObject('Sketch002').addConstraint(Sketcher.Constraint('DistanceY',4,2,5,2,298.221609)) 
App.getDocument('Joint_HouseMT_session_4').Sketch002.setExpression('Constraints[22]', u'<<BeamDims>>.Depth')
# Gui.getDocument('Joint_HouseMT_session_4').resetEdit()
App.ActiveDocument.recompute()
# ActiveSketch = App.getDocument('Joint_HouseMT_session_4').getObject('Sketch002')
# tv = ActiveSketch.ViewObject.TempoVis
# if tv:
#   tv.restore()
# ActiveSketch.ViewObject.TempoVis = None
# del(tv)
# del(ActiveSketch)
# 
# Gui.Selection.addSelection('Joint_HouseMT_session_4','Body001','Sketch002.')
App.getDocument('Joint_HouseMT_session_4').recompute()
# Gui.runCommand('PartDesign_Pocket',0)
# Gui.Selection.clearSelection()
# Gui.Selection.addSelection('Joint_HouseMT_session_4','Body001')
# Gui.ActiveDocument.ActiveView.setActiveObject('pdbody',App.getDocument('Joint_HouseMT_session_4').getObject('Body001'))
# Gui.Selection.clearSelection()
# Gui.Selection.addSelection('Joint_HouseMT_session_4','Body001','Sketch002.')
### Begin command PartDesign_Pocket
App.getDocument('Joint_HouseMT_session_4').getObject('Body001').newObject('PartDesign::Pocket','Pocket006')
App.getDocument('Joint_HouseMT_session_4').getObject('Pocket006').Profile = (App.getDocument('Joint_HouseMT_session_4').getObject('Sketch002'), ['',])
App.getDocument('Joint_HouseMT_session_4').getObject('Pocket006').Length = 5
App.ActiveDocument.recompute()
App.getDocument('Joint_HouseMT_session_4').getObject('Pocket006').ReferenceAxis = (App.getDocument('Joint_HouseMT_session_4').getObject('Sketch002'),['N_Axis'])
App.getDocument('Joint_HouseMT_session_4').getObject('Sketch002').Visibility = False
App.ActiveDocument.recompute()
# App.getDocument('Joint_HouseMT_session_4').getObject('Pocket006').ViewObject.ShapeAppearance=getattr(App.getDocument('Joint_HouseMT_session_4').getObject('Pocket005').getLinkedObject(True).ViewObject,'ShapeAppearance',App.getDocument('Joint_HouseMT_session_4').getObject('Pocket006').ViewObject.ShapeAppearance)
# App.getDocument('Joint_HouseMT_session_4').getObject('Pocket006').ViewObject.LineColor=getattr(App.getDocument('Joint_HouseMT_session_4').getObject('Pocket005').getLinkedObject(True).ViewObject,'LineColor',App.getDocument('Joint_HouseMT_session_4').getObject('Pocket006').ViewObject.LineColor)
# App.getDocument('Joint_HouseMT_session_4').getObject('Pocket006').ViewObject.PointColor=getattr(App.getDocument('Joint_HouseMT_session_4').getObject('Pocket005').getLinkedObject(True).ViewObject,'PointColor',App.getDocument('Joint_HouseMT_session_4').getObject('Pocket006').ViewObject.PointColor)
# App.getDocument('Joint_HouseMT_session_4').getObject('Pocket006').ViewObject.Transparency=getattr(App.getDocument('Joint_HouseMT_session_4').getObject('Pocket005').getLinkedObject(True).ViewObject,'Transparency',App.getDocument('Joint_HouseMT_session_4').getObject('Pocket006').ViewObject.Transparency)
# App.getDocument('Joint_HouseMT_session_4').getObject('Pocket006').ViewObject.DisplayMode=getattr(App.getDocument('Joint_HouseMT_session_4').getObject('Pocket005').getLinkedObject(True).ViewObject,'DisplayMode',App.getDocument('Joint_HouseMT_session_4').getObject('Pocket006').ViewObject.DisplayMode)
# Gui.getDocument('Joint_HouseMT_session_4').setEdit(App.getDocument('Joint_HouseMT_session_4').getObject('Body001'), 0, 'Pocket006.')
# Gui.Selection.clearSelection()
### End command PartDesign_Pocket
# Gui.Selection.clearSelection()
App.getDocument('Joint_HouseMT_session_4').Pocket006.setExpression('Length', u'<<MT1>>.TenonLength')
App.getDocument('Joint_HouseMT_session_4').getObject('Pocket006').TaperAngle = 0.000000
App.getDocument('Joint_HouseMT_session_4').getObject('Pocket006').UseCustomVector = 0
App.getDocument('Joint_HouseMT_session_4').getObject('Pocket006').Direction = (0, 0, -1)
App.getDocument('Joint_HouseMT_session_4').getObject('Pocket006').ReferenceAxis = (App.getDocument('Joint_HouseMT_session_4').getObject('Sketch002'), ['N_Axis'])
App.getDocument('Joint_HouseMT_session_4').getObject('Pocket006').AlongSketchNormal = 1
App.getDocument('Joint_HouseMT_session_4').getObject('Pocket006').SideType = 0
App.getDocument('Joint_HouseMT_session_4').getObject('Pocket006').Type = 0
App.getDocument('Joint_HouseMT_session_4').getObject('Pocket006').Type2 = 0
App.getDocument('Joint_HouseMT_session_4').getObject('Pocket006').UpToFace = None
App.getDocument('Joint_HouseMT_session_4').getObject('Pocket006').UpToFace2 = None
App.getDocument('Joint_HouseMT_session_4').getObject('Pocket006').Reversed = 1
App.getDocument('Joint_HouseMT_session_4').getObject('Pocket006').Offset = 0
App.getDocument('Joint_HouseMT_session_4').getObject('Pocket006').Offset2 = 0
App.getDocument('Joint_HouseMT_session_4').purgeTouched()
App.getDocument('Joint_HouseMT_session_4').recompute()
App.getDocument('Joint_HouseMT_session_4').getObject('Pocket005').Visibility = False
# Gui.getDocument('Joint_HouseMT_session_4').resetEdit()
App.getDocument('Joint_HouseMT_session_4').getObject('Sketch002').Visibility = False
# Gui.Selection.addSelection('Joint_HouseMT_session_4','Body001','Pocket006.')
# Gui.Selection.clearSelection()
# Gui.Selection.addSelection('Joint_HouseMT_session_4','Body002')
# Gui.ActiveDocument.ActiveView.setActiveObject('pdbody',App.getDocument('Joint_HouseMT_session_4').getObject('Body002'))
# Gui.Selection.clearSelection()
# Gui.Selection.addSelection('Joint_HouseMT_session_4','Body002','Pad004.')
### Begin command Std_Delete
App.getDocument('Joint_HouseMT_session_4').getObject('Body002').removeObject(App.getDocument('Joint_HouseMT_session_4').getObject('Pad004'))
App.getDocument('Joint_HouseMT_session_4').removeObject('Pad004')
App.getDocument('Joint_HouseMT_session_4').recompute()
### End command Std_Delete
# Gui.Selection.clearSelection()
# Gui.Selection.addSelection('Joint_HouseMT_session_4','Body002','Sketch008.')
# Gui.Selection.clearSelection()
# ActiveSketch = App.getDocument('Joint_HouseMT_session_4').getObject('Sketch008')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Joint_HouseMT_session_4').getObject('Body002'), 'Sketch008.'))
# if ActiveSketch.ViewObject.ShowSupport:
#   tv.show([ref[0] for ref in ActiveSketch.AttachmentSupport if not (ref[0].isDerivedFrom("App::Plane") or ref[0].isDerivedFrom("App::LocalCoordinateSystem"))])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
App.getDocument('Joint_HouseMT_session_4').getObject('Sketch008').setVisibility([0,1,2,3,4,5,6,7,8,9,10,11,12,13], True)
# ActiveSketch = App.getDocument('Joint_HouseMT_session_4').getObject('Sketch008')
# if ActiveSketch.ViewObject.RestoreCamera:
#   ActiveSketch.ViewObject.TempoVis.saveCamera()
#   if ActiveSketch.ViewObject.ForceOrtho:
#     ActiveSketch.ViewObject.Document.ActiveView.setCameraType('Orthographic')
# 
# Gui.Selection.addSelection('Joint_HouseMT_session_4','Body002','Sketch008.Vertex3',1333.5,152.414,-1.66896e-09,False)
# Gui.Selection.addSelection('Joint_HouseMT_session_4','Body002','Sketch008.Vertex8',1257.3,152.414,-1.66896e-09,False)
# Gui.Selection.clearSelection()
# Gui.Selection.addSelection('Joint_HouseMT_session_4','Body002','Sketch008.Vertex8',1257.3,152.414,-1.66896e-09,False)
# Gui.Selection.addSelection('Joint_HouseMT_session_4','Body002','Sketch008.Constraint10',1166.32,152.404,-63.2073,False)
# Gui.Selection.clearSelection()
App.getDocument('Joint_HouseMT_session_4').getObject('Sketch008').delConstraint(9)
App.getDocument('Joint_HouseMT_session_4').getObject('Sketch008').delConstraintOnPoint(3,2)
# Gui.Selection.addSelection('Joint_HouseMT_session_4','Body002','Sketch008.Constraint9',1379.19,152.404,-75.8483,False)
# Gui.Selection.clearSelection()
App.getDocument('Joint_HouseMT_session_4').getObject('Sketch008').delConstraint(8)
App.getDocument('Joint_HouseMT_session_4').getObject('Sketch008').moveGeometries([(3, 2)], App.Vector(-22.7091, -15.6774, 0))
App.getDocument('Joint_HouseMT_session_4').getObject('Sketch008').moveGeometries([(4, 1)], App.Vector(-61.1374, -41.4649, 0))
App.getDocument('Joint_HouseMT_session_4').getObject('Sketch008').moveGeometries([(3, 2)], App.Vector(-36.1083, -15.6774, 0))
App.getDocument('Joint_HouseMT_session_4').getObject('Sketch008').moveGeometries([(4, 1)], App.Vector(-57.3452, -3.28933, 0))
# Gui.runCommand('Std_Undo',0)
# Gui.runCommand('Std_Undo',0)
# Gui.runCommand('Std_Undo',0)
# Gui.runCommand('Std_Undo',0)
# Gui.runCommand('Std_Undo',0)
App.getDocument('Joint_HouseMT_session_4').getObject('Sketch008').moveGeometries([(1, 1)], App.Vector(-109.931, -15.4246, 0))
App.getDocument('Joint_HouseMT_session_4').getObject('Sketch008').moveGeometries([(4, 0)], App.Vector(-19.7198, -10.8739, 0), True)
# Gui.runCommand('Std_Undo',0)
# Gui.Selection.addSelection(App.getDocument('Joint_HouseMT_session_4').getObject('Body002'),['Sketch008.Vertex8','Sketch008.Vertex9'])
# Gui.Selection.clearSelection()
App.getDocument('Joint_HouseMT_session_4').getObject('Sketch008').moveGeometries([(3, 0)], App.Vector(4.42458, 37.986, 0), True)
# Gui.Selection.addSelection(App.getDocument('Joint_HouseMT_session_4').getObject('Body002'),['Sketch008.Edge5'])
App.getDocument('Joint_HouseMT_session_4').getObject('Sketch008').moveGeometries([(4, 0)], App.Vector(-89.4531, -22.5035, 0))
App.getDocument('Joint_HouseMT_session_4').getObject('Sketch008').moveGeometries([(1, 1), (4, 0)], App.Vector(2.59888, 16.9362, 0), True)
# Gui.Selection.addSelection('Joint_HouseMT_session_4','Body002','Sketch008.Constraint9',1415.85,152.404,-76.3539,False)
# Gui.Selection.clearSelection()
App.getDocument('Joint_HouseMT_session_4').getObject('Sketch008').delConstraint(8)
App.getDocument('Joint_HouseMT_session_4').getObject('Sketch008').delGeometries([4])
App.getDocument('Joint_HouseMT_session_4').getObject('Sketch008').moveGeometries([(1, 1)], App.Vector(-128.387, 32.8637, 0))
App.getDocument('Joint_HouseMT_session_4').getObject('Sketch008').moveGeometries([(1, 2)], App.Vector(-117.516, -30.8466, 0))
App.getDocument('Joint_HouseMT_session_4').getObject('Sketch008').moveGeometries([(1, 1)], App.Vector(-121.814, -7.84006, 0))
# Gui.Selection.addSelection('Joint_HouseMT_session_4','Body002','Sketch008.Vertex3',1333.5,152.414,-1.66896e-09,False)
# Gui.Selection.clearSelection()
# Gui.Selection.addSelection(App.getDocument('Joint_HouseMT_session_4').getObject('Sketch008'),['Sketch008.Constraint5'])
# Gui.Selection.clearSelection()
App.getDocument('Joint_HouseMT_session_4').getObject('Sketch008').delConstraint(4)
App.getDocument('Joint_HouseMT_session_4').getObject('Sketch008').moveGeometries([(1, 1)], App.Vector(-109.426, 52.8364, 0))
App.getDocument('Joint_HouseMT_session_4').getObject('Sketch008').moveGeometries([(3, 2)], App.Vector(-38.0999, 55.8702, 0))
# Gui.Selection.addSelection('Joint_HouseMT_session_4','Body002','Sketch008.Vertex8',1257.3,152.414,55.8702,False)
# Gui.Selection.addSelection('Joint_HouseMT_session_4','Body002','Sketch008.RootPoint',1219.2,152.41,-1.19213e-09,False)
### Begin command Sketcher_Dimension
App.getDocument('Joint_HouseMT_session_4').getObject('Sketch008').addConstraint(Sketcher.Constraint('Distance',3,2,-1,1,67.624620)) 
### End command Sketcher_Dimension
# Gui.Selection.clearSelection()
App.getDocument('Joint_HouseMT_session_4').getObject('Sketch008').addConstraint(Sketcher.Constraint('DistanceX',3,2,-1,1,38.100000)) 
App.getDocument('Joint_HouseMT_session_4').getObject('Sketch008').addConstraint(Sketcher.Constraint('Distance',3,2,-1,1,67.624620)) 
App.getDocument('Joint_HouseMT_session_4').getObject('Sketch008').addConstraint(Sketcher.Constraint('DistanceY',-1,1,3,2,55.870200)) 
App.getDocument('Joint_HouseMT_session_4').Sketch008.setExpression('Constraints[8]', u'<<DT1>>.TongueLength')
# Gui.Selection.addSelection('Joint_HouseMT_session_4','Body002','Sketch008.Vertex3',1333.5,152.414,52.8364,False)
# Gui.Selection.addSelection('Joint_HouseMT_session_4','Body002','Sketch008.RootPoint',1219.2,152.41,-1.19213e-09,False)
### Begin command Sketcher_Dimension
App.getDocument('Joint_HouseMT_session_4').getObject('Sketch008').addConstraint(Sketcher.Constraint('Distance',1,1,-1,1,125.921305)) 
### End command Sketcher_Dimension
# Gui.Selection.clearSelection()
App.getDocument('Joint_HouseMT_session_4').getObject('Sketch008').addConstraint(Sketcher.Constraint('DistanceY',-1,1,1,1,52.836400)) 
App.getDocument('Joint_HouseMT_session_4').Sketch008.setExpression('Constraints[9]', u'<<DT1>>.TongueLength')
# Gui.Selection.addSelection('Joint_HouseMT_session_4','Body002','Sketch008.Vertex6',1244.6,152.414,-38.214,False)
# Gui.Selection.addSelection('Joint_HouseMT_session_4','Body002','Sketch008.H_Axis',1261.88,152.402,-2.38452e-10,False)
### Begin command Sketcher_ConstrainCoincidentUnified
App.getDocument('Joint_HouseMT_session_4').getObject('Sketch008').addConstraint(Sketcher.Constraint('PointOnObject',2,2,-1))
### End command Sketcher_ConstrainCoincidentUnified
# Gui.Selection.clearSelection()
# Gui.Selection.addSelection('Joint_HouseMT_session_4','Body002','Sketch008.Vertex4',1346.2,152.414,-30.8466,False)
# Gui.Selection.addSelection('Joint_HouseMT_session_4','Body002','Sketch008.H_Axis',1352.14,152.402,-2.38452e-10,False)
### Begin command Sketcher_ConstrainCoincidentUnified
App.getDocument('Joint_HouseMT_session_4').getObject('Sketch008').addConstraint(Sketcher.Constraint('PointOnObject',1,2,-1))
### End command Sketcher_ConstrainCoincidentUnified
# Gui.Selection.clearSelection()
# Gui.Selection.addSelection('Joint_HouseMT_session_4','Body002','Sketch008.Constraint10',1267.19,152.404,75.3364,False)
# Gui.Selection.clearSelection()
App.getDocument('Joint_HouseMT_session_4').getObject('Sketch008').delConstraint(9)
# Gui.Selection.addSelection('Joint_HouseMT_session_4','Body002','Sketch008.Vertex3',1333.5,152.414,76.2,False)
# Gui.Selection.clearSelection()
App.getDocument('Joint_HouseMT_session_4').getObject('Sketch008').moveGeometries([(1, 1)], App.Vector(-138.248, 57.1334, 0))
# Gui.runCommand('Std_Undo',0)
# Gui.Selection.addSelection('Joint_HouseMT_session_4','Body002','Sketch008.Vertex3',1333.5,152.414,76.2,False)
# Gui.runCommand('Sketcher_CreatePolyline',0)
# Gui.Selection.clearSelection()
App.getDocument('Joint_HouseMT_session_4').getObject('Sketch008').addGeometry(Part.LineSegment(App.Vector(-114.300000,76.200000,0),App.Vector(-163.782666,87.724503,0)),False)
App.getDocument('Joint_HouseMT_session_4').getObject('Sketch008').addConstraint(Sketcher.Constraint('Coincident',1,1,4,1)) 
App.getDocument('Joint_HouseMT_session_4').getObject('Sketch008').addGeometry(Part.LineSegment(App.Vector(-163.782666,87.724503,0),App.Vector(-161.760083,-10.369118,0)),False)
App.getDocument('Joint_HouseMT_session_4').getObject('Sketch008').addConstraint(Sketcher.Constraint('Coincident',4,2,5,1)) 
App.getDocument('Joint_HouseMT_session_4').getObject('Sketch008').addConstraint(Sketcher.Constraint('Vertical',5)) 
App.getDocument('Joint_HouseMT_session_4').getObject('Sketch008').addGeometry(Part.LineSegment(App.Vector(-163.782666,-10.369118,0),App.Vector(0.000000,0.000000,0)),False)
App.getDocument('Joint_HouseMT_session_4').getObject('Sketch008').addConstraint(Sketcher.Constraint('Coincident',5,2,6,1)) 
App.getDocument('Joint_HouseMT_session_4').getObject('Sketch008').addConstraint(Sketcher.Constraint('Coincident',6,2,-1,1)) 
# Gui.runCommand('Sketcher_ConstrainVertical',0)
App.getDocument('Joint_HouseMT_session_4').getObject('Sketch008').moveGeometries([(6, 2)], App.Vector(-5.51814, -25.5382, 0))
App.getDocument('Joint_HouseMT_session_4').getObject('Sketch008').moveGeometries([(6, 2)], App.Vector(-7.28792, -27.308, 0))
App.getDocument('Joint_HouseMT_session_4').getObject('Sketch008').moveGeometries([(5, 2)], App.Vector(-169.597, -8.59938, 0))
App.getDocument('Joint_HouseMT_session_4').getObject('Sketch008').moveGeometries([(4, 2)], App.Vector(-173.137, 82.4153, 0))
# Gui.Selection.addSelection('Joint_HouseMT_session_4','Body002','Sketch008.Vertex14',1219.2,152.414,-1.66896e-09,False)
### Begin command Sketcher_Dimension
App.getDocument('Joint_HouseMT_session_4').getObject('Sketch008').addConstraint(Sketcher.Constraint('Distance',6,2,-1,1,0.000000)) 
### End command Sketcher_Dimension
# Gui.Selection.clearSelection()
# Gui.Selection.addSelection('Joint_HouseMT_session_4','Body002','Sketch008.Edge6',1392.34,152.408,80.6456,False)
# Gui.Selection.addSelection('Joint_HouseMT_session_4','Body002','Sketch008.Vertex12',1392.34,152.414,-8.59938,False)
# Gui.Selection.addSelection('Joint_HouseMT_session_4','Body002','Sketch008.H_Axis',1411.8,152.402,-2.38452e-10,False)
### Begin command Sketcher_ConstrainCoincidentUnified
App.getDocument('Joint_HouseMT_session_4').getObject('Sketch008').addConstraint(Sketcher.Constraint('PointOnObject',5,2,-1))
### End command Sketcher_ConstrainCoincidentUnified
# Gui.Selection.clearSelection()
# Gui.Selection.addSelection('Joint_HouseMT_session_4','Body002','Sketch008.Vertex12',1392.34,152.414,-1.66896e-09,False)
# Gui.Selection.addSelection('Joint_HouseMT_session_4','Body002','Sketch008.Vertex14',1219.2,152.414,-1.66896e-09,False)
### Begin command Sketcher_Dimension
App.getDocument('Joint_HouseMT_session_4').getObject('Sketch008').addConstraint(Sketcher.Constraint('Distance',5,2,6,2,173.137000)) 
### End command Sketcher_Dimension
# Gui.Selection.clearSelection()
App.getDocument('Joint_HouseMT_session_4').getObject('Sketch008').addConstraint(Sketcher.Constraint('DistanceX',5,2,6,2,173.137000)) 
App.getDocument('Joint_HouseMT_session_4').Sketch008.setExpression('Constraints[17]', u'<<JoistDims>>.Depth')
# Gui.Selection.addSelection('Joint_HouseMT_session_4','Body002','Sketch008.Vertex10',1371.6,152.414,82.4153,False)
# Gui.Selection.addSelection('Joint_HouseMT_session_4','Body002','Sketch008.Vertex14',1219.2,152.414,-1.66896e-09,False)
### Begin command Sketcher_Dimension
App.getDocument('Joint_HouseMT_session_4').getObject('Sketch008').addConstraint(Sketcher.Constraint('Distance',4,2,6,2,173.257155)) 
### End command Sketcher_Dimension
# Gui.Selection.clearSelection()
App.getDocument('Joint_HouseMT_session_4').getObject('Sketch008').addConstraint(Sketcher.Constraint('DistanceY',6,2,4,2,82.415300)) 
App.getDocument('Joint_HouseMT_session_4').getObject('Sketch008').addConstraint(Sketcher.Constraint('Distance',4,2,6,2,173.257155)) 
App.getDocument('Joint_HouseMT_session_4').getObject('Sketch008').addConstraint(Sketcher.Constraint('DistanceY',6,2,4,2,82.415300)) 
App.getDocument('Joint_HouseMT_session_4').Sketch008.setExpression('Constraints[18]', u'<<DT1>>.TongueLength')
App.getDocument('Joint_HouseMT_session_4').getObject('Sketch008').moveGeometries([(1, 1)], App.Vector(-112.966, 94.8034, 0))
### Begin command Std_Save
# Gui.SendMsgToActiveView("Save")
App.getDocument("Joint_HouseMT_session_4").save()
### End command Std_Save
# Gui.Selection.addSelection('Joint_HouseMT_session_4','Body002','Sketch008.Vertex3',1333.5,152.414,94.8034,False)
# Gui.Selection.addSelection('Joint_HouseMT_session_4','Body002','Sketch008.V_Axis',1219.2,152.402,-1.52046,False)
# Gui.Selection.removeSelection('Joint_HouseMT_session_4','Body002','Sketch008.V_Axis')
# Gui.Selection.addSelection('Joint_HouseMT_session_4','Body002','Sketch008.Vertex14',1219.2,152.414,-1.66896e-09,False)
### Begin command Sketcher_Dimension
App.getDocument('Joint_HouseMT_session_4').getObject('Sketch008').addConstraint(Sketcher.Constraint('Distance',1,1,6,2,148.499746)) 
### End command Sketcher_Dimension
# Gui.Selection.clearSelection()
App.getDocument('Joint_HouseMT_session_4').getObject('Sketch008').addConstraint(Sketcher.Constraint('DistanceY',6,2,1,1,94.803400)) 
App.getDocument('Joint_HouseMT_session_4').getObject('Sketch008').addConstraint(Sketcher.Constraint('Distance',1,1,6,2,148.499746)) 
App.getDocument('Joint_HouseMT_session_4').getObject('Sketch008').addConstraint(Sketcher.Constraint('DistanceY',6,2,1,1,94.803400)) 
App.getDocument('Joint_HouseMT_session_4').Sketch008.setExpression('Constraints[19]', u'<<DT1>>.TongueLength')
App.getDocument('Joint_HouseMT_session_4').getObject('Sketch008').moveGeometries([(0, 2)], App.Vector(-76.1999, 54.6053, 0))
App.getDocument('Joint_HouseMT_session_4').getObject('Sketch008').moveGeometries([(0, 1)], App.Vector(-78.0771, 12.8902, 0))
# Gui.Selection.addSelection('Joint_HouseMT_session_4','Body002','Sketch008.Edge4',1252.01,152.408,44.4527,False)
App.getDocument('Joint_HouseMT_session_4').getObject('Sketch008').moveGeometries([(2, 2), (3, 0)], App.Vector(6.73525, 66.4877, 0), True)
# Gui.Selection.clearSelection()
# Gui.Selection.addSelection('Joint_HouseMT_session_4','Body002','Sketch008.Vertex8',1257.3,152.414,76.2,False)
# Gui.runCommand('Sketcher_CreatePolyline',0)
# Gui.Selection.clearSelection()
App.getDocument('Joint_HouseMT_session_4').getObject('Sketch008').addGeometry(Part.LineSegment(App.Vector(-38.100000,76.200000,0),App.Vector(0.000000,75.842026,0)),False)
App.getDocument('Joint_HouseMT_session_4').getObject('Sketch008').addConstraint(Sketcher.Constraint('Coincident',3,2,7,1)) 
App.getDocument('Joint_HouseMT_session_4').getObject('Sketch008').addConstraint(Sketcher.Constraint('PointOnObject',7,2,-2)) 
App.getDocument('Joint_HouseMT_session_4').getObject('Sketch008').addConstraint(Sketcher.Constraint('Horizontal',7)) 
App.getDocument('Joint_HouseMT_session_4').getObject('Sketch008').addGeometry(Part.LineSegment(App.Vector(0.000000,76.200000,0),App.Vector(0.000000,0.000000,0)),False)
App.getDocument('Joint_HouseMT_session_4').getObject('Sketch008').addConstraint(Sketcher.Constraint('Coincident',7,2,8,1)) 
App.getDocument('Joint_HouseMT_session_4').getObject('Sketch008').addConstraint(Sketcher.Constraint('Coincident',8,2,6,2)) 
App.getDocument('Joint_HouseMT_session_4').getObject('Sketch008').addGeometry(Part.LineSegment(App.Vector(0.000000,0.000000,0),App.Vector(-25.400000,0.000000,0)),False)
App.getDocument('Joint_HouseMT_session_4').getObject('Sketch008').addConstraint(Sketcher.Constraint('Coincident',8,2,9,1)) 
App.getDocument('Joint_HouseMT_session_4').getObject('Sketch008').addConstraint(Sketcher.Constraint('Coincident',9,2,2,2)) 
App.getDocument('Joint_HouseMT_session_4').getObject('Sketch008').addConstraint(Sketcher.Constraint('Horizontal',9)) 
# Gui.runCommand('Std_Undo',0)
# Gui.Selection.addSelection('Joint_HouseMT_session_4','Body002','Sketch008.Vertex4',1346.2,152.414,-1.66896e-09,False)
# Gui.Selection.addSelection('Joint_HouseMT_session_4','Body002','Sketch008.Constraint6',1245.8,152.404,-1.75502,False)
# Gui.Selection.addSelection('Joint_HouseMT_session_4','Body002','Sketch008.Vertex20',1244.6,152.414,-1.66896e-09,False)
App.getDocument('Joint_HouseMT_session_4').getObject('Sketch008').moveGeometries([(9, 2), (1, 2)], App.Vector(12.6917, -15.3419, 0), True)
App.getDocument('Joint_HouseMT_session_4').getObject('Sketch008').moveGeometries([(9, 2), (1, 2)], App.Vector(-3.08792, 9.26378, 0), True)
App.getDocument('Joint_HouseMT_session_4').getObject('Sketch008').moveGeometries([(9, 2), (1, 2)], App.Vector(-2.77917, -4.9407, 0), True)
# Gui.Selection.addSelection('Joint_HouseMT_session_4','Body002','Sketch008.Vertex6',1244.6,152.414,-1.66896e-09,False)
### Begin command Sketcher_ConstrainCoincidentUnified
App.getDocument('Joint_HouseMT_session_4').getObject('Sketch008').addConstraint(Sketcher.Constraint('Coincident',1,2,9,2))
App.getDocument('Joint_HouseMT_session_4').getObject('Sketch008').addConstraint(Sketcher.Constraint('Coincident',1,2,2,2))
### End command Sketcher_ConstrainCoincidentUnified
# Gui.Selection.clearSelection()
# Gui.runCommand('Std_Undo',0)
# Gui.Selection.addSelection('Joint_HouseMT_session_4','Body002','Sketch008.Vertex20',1237.78,152.414,-11.0188,False)
# Gui.Selection.clearSelection()
# Gui.Selection.addSelection('Joint_HouseMT_session_4','Body002','Sketch008.Vertex20',1237.78,152.414,-11.0188,False)
# Gui.Selection.clearSelection()
App.getDocument('Joint_HouseMT_session_4').getObject('Sketch008').moveGeometries([(9, 2)], App.Vector(-16.4919, -16.3167, 0))
### Begin command Sketcher_DeleteAllGeometry
App.getDocument('Joint_HouseMT_session_4').getObject('Sketch008').deleteAllGeometry()
### End command Sketcher_DeleteAllGeometry
# Gui.runCommand('Std_Undo',0)
# Gui.Selection.addSelection('Joint_HouseMT_session_4','Body002','Sketch008.Vertex20',1235.69,152.414,-16.3167,False)
# Gui.Selection.clearSelection()
# Gui.Selection.addSelection('Joint_HouseMT_session_4','Body002','Sketch008.Edge10',0,0,0,False)
# Gui.Selection.clearSelection()
# Gui.Selection.addSelection('Joint_HouseMT_session_4','Body002','Sketch008.Edge10',0,0,0,False)
# Gui.Selection.clearSelection()
App.getDocument('Joint_HouseMT_session_4').getObject('Sketch008').delGeometries([9])
# Gui.getDocument('Joint_HouseMT_session_4').resetEdit()
App.ActiveDocument.recompute()
# ActiveSketch = App.getDocument('Joint_HouseMT_session_4').getObject('Sketch008')
# tv = ActiveSketch.ViewObject.TempoVis
# if tv:
#   tv.restore()
# ActiveSketch.ViewObject.TempoVis = None
# del(tv)
# del(ActiveSketch)
# 
# Gui.Selection.addSelection('Joint_HouseMT_session_4','Body002','Sketch008.')
App.getDocument('Joint_HouseMT_session_4').recompute()
### Begin command PartDesign_Pocket
App.getDocument('Joint_HouseMT_session_4').getObject('Body002').newObject('PartDesign::Pocket','Pocket007')
App.getDocument('Joint_HouseMT_session_4').getObject('Pocket007').Profile = (App.getDocument('Joint_HouseMT_session_4').getObject('Sketch008'), ['',])
App.getDocument('Joint_HouseMT_session_4').getObject('Pocket007').Length = 5
App.ActiveDocument.recompute()
App.getDocument('Joint_HouseMT_session_4').getObject('Pocket007').ReferenceAxis = (App.getDocument('Joint_HouseMT_session_4').getObject('Sketch008'),['N_Axis'])
App.getDocument('Joint_HouseMT_session_4').getObject('Sketch008').Visibility = False
App.ActiveDocument.recompute()
# App.getDocument('Joint_HouseMT_session_4').getObject('Pocket007').ViewObject.ShapeAppearance=getattr(App.getDocument('Joint_HouseMT_session_4').getObject('Pad003').getLinkedObject(True).ViewObject,'ShapeAppearance',App.getDocument('Joint_HouseMT_session_4').getObject('Pocket007').ViewObject.ShapeAppearance)
# App.getDocument('Joint_HouseMT_session_4').getObject('Pocket007').ViewObject.LineColor=getattr(App.getDocument('Joint_HouseMT_session_4').getObject('Pad003').getLinkedObject(True).ViewObject,'LineColor',App.getDocument('Joint_HouseMT_session_4').getObject('Pocket007').ViewObject.LineColor)
# App.getDocument('Joint_HouseMT_session_4').getObject('Pocket007').ViewObject.PointColor=getattr(App.getDocument('Joint_HouseMT_session_4').getObject('Pad003').getLinkedObject(True).ViewObject,'PointColor',App.getDocument('Joint_HouseMT_session_4').getObject('Pocket007').ViewObject.PointColor)
# App.getDocument('Joint_HouseMT_session_4').getObject('Pocket007').ViewObject.Transparency=getattr(App.getDocument('Joint_HouseMT_session_4').getObject('Pad003').getLinkedObject(True).ViewObject,'Transparency',App.getDocument('Joint_HouseMT_session_4').getObject('Pocket007').ViewObject.Transparency)
# App.getDocument('Joint_HouseMT_session_4').getObject('Pocket007').ViewObject.DisplayMode=getattr(App.getDocument('Joint_HouseMT_session_4').getObject('Pad003').getLinkedObject(True).ViewObject,'DisplayMode',App.getDocument('Joint_HouseMT_session_4').getObject('Pocket007').ViewObject.DisplayMode)
# Gui.getDocument('Joint_HouseMT_session_4').setEdit(App.getDocument('Joint_HouseMT_session_4').getObject('Body002'), 0, 'Pocket007.')
# Gui.Selection.clearSelection()
### End command PartDesign_Pocket
# Gui.Selection.clearSelection()
App.getDocument('Joint_HouseMT_session_4').Pocket007.setExpression('Length', u'<<DT1>>.TongueDepth')
App.getDocument('Joint_HouseMT_session_4').getObject('Pocket007').TaperAngle = 0.000000
App.getDocument('Joint_HouseMT_session_4').getObject('Pocket007').UseCustomVector = 0
App.getDocument('Joint_HouseMT_session_4').getObject('Pocket007').Direction = (0, -1, 0)
App.getDocument('Joint_HouseMT_session_4').getObject('Pocket007').ReferenceAxis = (App.getDocument('Joint_HouseMT_session_4').getObject('Sketch008'), ['N_Axis'])
App.getDocument('Joint_HouseMT_session_4').getObject('Pocket007').AlongSketchNormal = 1
App.getDocument('Joint_HouseMT_session_4').getObject('Pocket007').SideType = 0
App.getDocument('Joint_HouseMT_session_4').getObject('Pocket007').Type = 0
App.getDocument('Joint_HouseMT_session_4').getObject('Pocket007').Type2 = 0
App.getDocument('Joint_HouseMT_session_4').getObject('Pocket007').UpToFace = None
App.getDocument('Joint_HouseMT_session_4').getObject('Pocket007').UpToFace2 = None
App.getDocument('Joint_HouseMT_session_4').getObject('Pocket007').Reversed = 0
App.getDocument('Joint_HouseMT_session_4').getObject('Pocket007').Offset = 0
App.getDocument('Joint_HouseMT_session_4').getObject('Pocket007').Offset2 = 0
App.getDocument('Joint_HouseMT_session_4').purgeTouched()
App.getDocument('Joint_HouseMT_session_4').recompute()
App.getDocument('Joint_HouseMT_session_4').getObject('Pad003').Visibility = False
# Gui.getDocument('Joint_HouseMT_session_4').resetEdit()
App.getDocument('Joint_HouseMT_session_4').getObject('Sketch008').Visibility = False
# Gui.runCommand('Std_Undo',0)
# Gui.Selection.addSelection('Joint_HouseMT_session_4','Body002','DatumPlane002.')
# Gui.runCommand('Std_Undo',0)
# Gui.runCommand('Std_Undo',0)
# Gui.runCommand('Std_Redo',0)
# Gui.runCommand('Std_Redo',0)
# Gui.runCommand('Std_Redo',0)
# Gui.Selection.clearSelection()
# Gui.Selection.addSelection('Joint_HouseMT_session_4','Body002','Pocket007.')
# Gui.ActiveDocument.setEdit(App.getDocument('Joint_HouseMT_session_4').getObject('Pocket007'), 0)
# Gui.Selection.clearSelection()
App.getDocument('Joint_HouseMT_session_4').Pocket007.setExpression('Length', u'<<DT1>>.TongueDepth')
App.getDocument('Joint_HouseMT_session_4').getObject('Pocket007').TaperAngle = 0.000000
App.getDocument('Joint_HouseMT_session_4').getObject('Pocket007').UseCustomVector = 0
App.getDocument('Joint_HouseMT_session_4').getObject('Pocket007').Direction = (0, -1, 0)
App.getDocument('Joint_HouseMT_session_4').getObject('Pocket007').ReferenceAxis = (App.getDocument('Joint_HouseMT_session_4').getObject('Sketch008'), ['N_Axis'])
App.getDocument('Joint_HouseMT_session_4').getObject('Pocket007').AlongSketchNormal = 1
App.getDocument('Joint_HouseMT_session_4').getObject('Pocket007').SideType = 0
App.getDocument('Joint_HouseMT_session_4').getObject('Pocket007').Type = 0
App.getDocument('Joint_HouseMT_session_4').getObject('Pocket007').Type2 = 0
App.getDocument('Joint_HouseMT_session_4').getObject('Pocket007').UpToFace = None
App.getDocument('Joint_HouseMT_session_4').getObject('Pocket007').UpToFace2 = None
App.getDocument('Joint_HouseMT_session_4').getObject('Pocket007').Reversed = 0
App.getDocument('Joint_HouseMT_session_4').getObject('Pocket007').Offset = 0
App.getDocument('Joint_HouseMT_session_4').getObject('Pocket007').Offset2 = 0
App.getDocument('Joint_HouseMT_session_4').purgeTouched()
App.getDocument('Joint_HouseMT_session_4').recompute()
App.getDocument('Joint_HouseMT_session_4').getObject('Pad003').Visibility = False
# Gui.getDocument('Joint_HouseMT_session_4').resetEdit()
App.getDocument('Joint_HouseMT_session_4').getObject('Sketch008').Visibility = False
# Gui.Selection.addSelection('Joint_HouseMT_session_4','Body002','Pocket007.Sketch008.')
# Gui.Selection.clearSelection()
# ActiveSketch = App.getDocument('Joint_HouseMT_session_4').getObject('Sketch008')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Joint_HouseMT_session_4').getObject('Body002'), 'Pocket007.Sketch008.'))
# if ActiveSketch.ViewObject.ShowSupport:
#   tv.show([ref[0] for ref in ActiveSketch.AttachmentSupport if not (ref[0].isDerivedFrom("App::Plane") or ref[0].isDerivedFrom("App::LocalCoordinateSystem"))])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
App.getDocument('Joint_HouseMT_session_4').getObject('Sketch008').setVisibility([0,1,2,3,4,5,6,7,8,9,10,11,12,13,14,15,16,17,18,19,20,21,22,23,24], True)
# ActiveSketch = App.getDocument('Joint_HouseMT_session_4').getObject('Sketch008')
# if ActiveSketch.ViewObject.RestoreCamera:
#   ActiveSketch.ViewObject.TempoVis.saveCamera()
#   if ActiveSketch.ViewObject.ForceOrtho:
#     ActiveSketch.ViewObject.Document.ActiveView.setCameraType('Orthographic')
# 
App.getDocument('Joint_HouseMT_session_4').getObject('Sketch008').moveGeometries([(6, 2)], App.Vector(1.47014, -4.60604, 0))
# Gui.Selection.addSelection('Joint_HouseMT_session_4','Body002','Pocket007.Sketch008.Edge9',1219.2,152.408,0.544738,False)
# Gui.Selection.removeSelection('Joint_HouseMT_session_4','Body002','Pocket007.Sketch008.Edge9')
# Gui.Selection.addSelection('Joint_HouseMT_session_4','Body002','Pocket007.Sketch008.Edge9',1219.2,152.408,27.9145,False)
# Gui.Selection.clearSelection()
App.getDocument('Joint_HouseMT_session_4').getObject('Sketch008').delGeometries([8])
# Gui.Selection.addSelection('Joint_HouseMT_session_4','Body002','Pocket007.Sketch008.V_Axis',1219.2,152.402,52.6585,False)
# Gui.Selection.clearSelection()
# Gui.Selection.addSelection('Joint_HouseMT_session_4','Body002','Pocket007.Sketch008.Vertex16',1219.2,152.414,76.2,False)
# Gui.Selection.addSelection('Joint_HouseMT_session_4','Body002','Pocket007.Sketch008.Edge8',1229.45,152.408,76.2,False)
# Gui.Selection.clearSelection()
App.getDocument('Joint_HouseMT_session_4').getObject('Sketch008').delGeometries([7])
# Gui.Selection.addSelection('Joint_HouseMT_session_4','Body002','Pocket007.Sketch008.Edge7',1238.23,152.408,-9.53708e-10,False)
# Gui.Selection.clearSelection()
# Gui.Selection.addSelection('Joint_HouseMT_session_4','Body002','Pocket007.Sketch008.Edge5',1349.23,152.408,76.2,False)
# Gui.Selection.addSelection('Joint_HouseMT_session_4','Body002','Pocket007.Sketch008.Edge6',1371.6,152.408,62.96,False)
# Gui.Selection.clearSelection()
App.getDocument('Joint_HouseMT_session_4').getObject('Sketch008').delGeometries([4,5])
# Gui.Selection.addSelection('Joint_HouseMT_session_4','Body002','Pocket007.Sketch008.Constraint14',1371.55,152.404,-0.667209,False)
# Gui.Selection.clearSelection()
App.getDocument('Joint_HouseMT_session_4').getObject('Sketch008').delConstraint(13)
# Gui.Selection.addSelection('Joint_HouseMT_session_4','Body002','Pocket007.Sketch008.Vertex9',1371.6,152.414,-1.66896e-09,False)
# Gui.Selection.clearSelection()
# Gui.Selection.addSelection('Joint_HouseMT_session_4','Body002','Pocket007.Sketch008.Edge5',1363.69,152.408,-9.53708e-10,False)
# Gui.Selection.clearSelection()
# Gui.Selection.addSelection('Joint_HouseMT_session_4','Body002','Pocket007.Sketch008.Constraint14',1363.64,152.404,-1.1065,False)
# Gui.Selection.addSelection('Joint_HouseMT_session_4','Body002','Pocket007.Sketch008.Vertex9',1371.6,152.414,-1.66896e-09,False)
# Gui.Selection.clearSelection()
App.getDocument('Joint_HouseMT_session_4').getObject('Sketch008').delConstraint(13)
# Gui.Selection.addSelection('Joint_HouseMT_session_4','Body002','Pocket007.Sketch008.Edge5',1362.53,152.408,-9.53708e-10,False)
# Gui.Selection.clearSelection()
App.getDocument('Joint_HouseMT_session_4').getObject('Sketch008').delGeometries([4])
# Gui.Selection.addSelection('Joint_HouseMT_session_4','Body002','Pocket007.Sketch008.Vertex3',1333.5,152.414,76.2,False)
# Gui.Selection.clearSelection()
# Gui.Selection.addSelection('Joint_HouseMT_session_4','Body002','Pocket007.Sketch008.Vertex3',1333.5,152.414,76.2,False)
# Gui.runCommand('Sketcher_CreatePolyline',0)
# Gui.Selection.clearSelection()
App.getDocument('Joint_HouseMT_session_4').getObject('Sketch008').addGeometry(Part.LineSegment(App.Vector(-114.300000,76.200000,0),App.Vector(-38.100000,76.200000,0)),False)
App.getDocument('Joint_HouseMT_session_4').getObject('Sketch008').addConstraint(Sketcher.Constraint('Coincident',1,1,4,1)) 
App.getDocument('Joint_HouseMT_session_4').getObject('Sketch008').addConstraint(Sketcher.Constraint('Coincident',4,2,3,2)) 
App.getDocument('Joint_HouseMT_session_4').getObject('Sketch008').addConstraint(Sketcher.Constraint('Horizontal',4)) 
# Gui.runCommand('Sketcher_CompCreateRectangles',0)
ActiveSketch = App.getDocument('Joint_HouseMT_session_4').getObject('Sketch008')

lastGeoId = len(ActiveSketch.Geometry)

geoList = []
geoList.append(Part.LineSegment(App.Vector(0.000000, 0.000000, 0.000000),App.Vector(0.000000, 83.588562, 0.000000)))
geoList.append(Part.LineSegment(App.Vector(0.000000, 83.588562, 0.000000),App.Vector(-178.763634, 83.588562, 0.000000)))
geoList.append(Part.LineSegment(App.Vector(-178.763634, 83.588562, 0.000000),App.Vector(-178.763634, 0.000000, 0.000000)))
geoList.append(Part.LineSegment(App.Vector(-178.763634, 0.000000, 0.000000),App.Vector(0.000000, 0.000000, 0.000000)))
App.getDocument('Joint_HouseMT_session_4').getObject('Sketch008').addGeometry(geoList,False)
del geoList

constraintList = []
constraintList.append(Sketcher.Constraint('Coincident', 5, 2, 6, 1))
constraintList.append(Sketcher.Constraint('Coincident', 6, 2, 7, 1))
constraintList.append(Sketcher.Constraint('Coincident', 7, 2, 8, 1))
constraintList.append(Sketcher.Constraint('Coincident', 8, 2, 5, 1))
constraintList.append(Sketcher.Constraint('Vertical', 5))
constraintList.append(Sketcher.Constraint('Vertical', 7))
constraintList.append(Sketcher.Constraint('Horizontal', 6))
constraintList.append(Sketcher.Constraint('Horizontal', 8))
App.getDocument('Joint_HouseMT_session_4').getObject('Sketch008').addConstraint(constraintList)
del constraintList

App.getDocument('Joint_HouseMT_session_4').getObject('Sketch008').addConstraint(Sketcher.Constraint('Coincident', 5, 1, -1, 1))


# Gui.Selection.addSelection('Joint_HouseMT_session_4','Body002','Pocket007.Sketch008.Vertex16',1397.96,152.414,-1.66896e-09,False)
# Gui.Selection.addSelection('Joint_HouseMT_session_4','Body002','Pocket007.Sketch008.Vertex11',1219.2,152.414,-1.66896e-09,False)
### Begin command Sketcher_Dimension
App.getDocument('Joint_HouseMT_session_4').getObject('Sketch008').addConstraint(Sketcher.Constraint('Distance',7,2,5,1,178.763634)) 
### End command Sketcher_Dimension
# Gui.Selection.clearSelection()
App.getDocument('Joint_HouseMT_session_4').getObject('Sketch008').addConstraint(Sketcher.Constraint('DistanceX',7,2,5,1,178.763634)) 
App.getDocument('Joint_HouseMT_session_4').Sketch008.setExpression('Constraints[23]', u'<<JoistDims>>.Width')
# Gui.Selection.addSelection('Joint_HouseMT_session_4','Body002','Pocket007.Sketch008.Vertex12',1219.2,152.414,83.5886,False)
# Gui.Selection.addSelection('Joint_HouseMT_session_4','Body002','Pocket007.Sketch008.Vertex11',1219.2,152.414,-1.66896e-09,False)
### Begin command Sketcher_Dimension
App.getDocument('Joint_HouseMT_session_4').getObject('Sketch008').addConstraint(Sketcher.Constraint('Distance',5,2,5,1,83.588562)) 
### End command Sketcher_Dimension
# Gui.Selection.clearSelection()
App.getDocument('Joint_HouseMT_session_4').getObject('Sketch008').addConstraint(Sketcher.Constraint('DistanceY',5,1,5,2,83.588562)) 
App.getDocument('Joint_HouseMT_session_4').Sketch008.setExpression('Constraints[24]', u'<<DT1>>.TongueLength')
# Gui.getDocument('Joint_HouseMT_session_4').resetEdit()
App.ActiveDocument.recompute()
# ActiveSketch = App.getDocument('Joint_HouseMT_session_4').getObject('Sketch008')
# tv = ActiveSketch.ViewObject.TempoVis
# if tv:
#   tv.restore()
# ActiveSketch.ViewObject.TempoVis = None
# del(tv)
# del(ActiveSketch)
# 
# Gui.Selection.addSelection('Joint_HouseMT_session_4','Body002','Pocket007.Sketch008.')
App.getDocument('Joint_HouseMT_session_4').recompute()
# Gui.Selection.clearSelection()
# ActiveSketch = App.getDocument('Joint_HouseMT_session_4').getObject('Sketch008')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Joint_HouseMT_session_4').getObject('Body002'), 'Pocket007.Sketch008.'))
# if ActiveSketch.ViewObject.ShowSupport:
#   tv.show([ref[0] for ref in ActiveSketch.AttachmentSupport if not (ref[0].isDerivedFrom("App::Plane") or ref[0].isDerivedFrom("App::LocalCoordinateSystem"))])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
App.getDocument('Joint_HouseMT_session_4').getObject('Sketch008').setVisibility([0,1,2,3,4,5,6,7,8,9,10,11,12,13,14,15,16,17,18,19,20,21,22,23,24], True)
# ActiveSketch = App.getDocument('Joint_HouseMT_session_4').getObject('Sketch008')
# if ActiveSketch.ViewObject.RestoreCamera:
#   ActiveSketch.ViewObject.TempoVis.saveCamera()
#   if ActiveSketch.ViewObject.ForceOrtho:
#     ActiveSketch.ViewObject.Document.ActiveView.setCameraType('Orthographic')
# 
# Gui.Selection.addSelection('Joint_HouseMT_session_4','Body002','Pocket007.Sketch008.Edge5',1282.59,152.408,76.2,False)
# Gui.Selection.clearSelection()
App.getDocument('Joint_HouseMT_session_4').getObject('Sketch008').delGeometries([4])
# Gui.Selection.addSelection('Joint_HouseMT_session_4','Body002','Pocket007.Sketch008.Edge6',1286.19,152.408,76.2,False)
# Gui.Selection.clearSelection()
App.getDocument('Joint_HouseMT_session_4').getObject('Sketch008').delGeometries([5])
# Gui.Selection.addSelection('Joint_HouseMT_session_4','Body002','Pocket007.Sketch008.Vertex8',1257.3,152.414,76.2,False)
# Gui.Selection.addSelection('Joint_HouseMT_session_4','Body002','Pocket007.Sketch008.Vertex10',1219.2,152.414,76.2,False)
# Gui.runCommand('Sketcher_CreateLine',0)
# Gui.Selection.clearSelection()
ActiveSketch = App.getDocument('Joint_HouseMT_session_4').getObject('Sketch008')

lastGeoId = len(ActiveSketch.Geometry)

geoList = []
geoList.append(Part.LineSegment(App.Vector(-38.100000, 76.200000, 0.000000),App.Vector(0.000000, 76.200000, 0.000000)))
App.getDocument('Joint_HouseMT_session_4').getObject('Sketch008').addGeometry(geoList,False)
del geoList

constraintList = []
constraintList = []
constraintList.append(Sketcher.Constraint('Coincident', 7, 1, 3, 2))
constraintList.append(Sketcher.Constraint('Coincident', 7, 2, 4, 2))
App.getDocument('Joint_HouseMT_session_4').getObject('Sketch008').addConstraint(constraintList)
del constraintList

ActiveSketch = App.getDocument('Joint_HouseMT_session_4').getObject('Sketch008')

lastGeoId = len(ActiveSketch.Geometry)

geoList = []
geoList.append(Part.LineSegment(App.Vector(-114.300000, 76.200000, 0.000000),App.Vector(-152.400000, 76.200000, 0.000000)))
App.getDocument('Joint_HouseMT_session_4').getObject('Sketch008').addGeometry(geoList,False)
del geoList

constraintList = []
constraintList = []
constraintList.append(Sketcher.Constraint('Coincident', 8, 1, 1, 1))
constraintList.append(Sketcher.Constraint('Coincident', 8, 2, 5, 1))
constraintList.append(Sketcher.Constraint('Horizontal', 8))
App.getDocument('Joint_HouseMT_session_4').getObject('Sketch008').addConstraint(constraintList)
del constraintList

App.getDocument('Joint_HouseMT_session_4').getObject('Sketch008').moveGeometries([(5, 1)], App.Vector(-188.816, 86.9065, 0))
# Gui.Selection.addSelection('Joint_HouseMT_session_4','Body002','Pocket007.Sketch008.Vertex11',1371.6,152.414,86.9065,False)
# Gui.Selection.addSelection('Joint_HouseMT_session_4','Body002','Pocket007.Sketch008.Vertex9',1219.2,152.414,-1.66896e-09,False)
### Begin command Sketcher_Dimension
App.getDocument('Joint_HouseMT_session_4').getObject('Sketch008').addConstraint(Sketcher.Constraint('Distance',5,1,4,1,175.438023)) 
### End command Sketcher_Dimension
# Gui.Selection.clearSelection()
App.getDocument('Joint_HouseMT_session_4').getObject('Sketch008').addConstraint(Sketcher.Constraint('DistanceY',4,1,5,1,86.906500)) 
App.getDocument('Joint_HouseMT_session_4').Sketch008.setExpression('Constraints[24]', u'<<DT1>>.TongueLength')
# Gui.getDocument('Joint_HouseMT_session_4').resetEdit()
App.ActiveDocument.recompute()
# ActiveSketch = App.getDocument('Joint_HouseMT_session_4').getObject('Sketch008')
# tv = ActiveSketch.ViewObject.TempoVis
# if tv:
#   tv.restore()
# ActiveSketch.ViewObject.TempoVis = None
# del(tv)
# del(ActiveSketch)
# 
# Gui.Selection.addSelection('Joint_HouseMT_session_4','Body002','Pocket007.Sketch008.')
App.getDocument('Joint_HouseMT_session_4').recompute()
# Gui.Selection.clearSelection()
# ActiveSketch = App.getDocument('Joint_HouseMT_session_4').getObject('Sketch008')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Joint_HouseMT_session_4').getObject('Body002'), 'Pocket007.Sketch008.'))
# if ActiveSketch.ViewObject.ShowSupport:
#   tv.show([ref[0] for ref in ActiveSketch.AttachmentSupport if not (ref[0].isDerivedFrom("App::Plane") or ref[0].isDerivedFrom("App::LocalCoordinateSystem"))])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
App.getDocument('Joint_HouseMT_session_4').getObject('Sketch008').setVisibility([0,1,2,3,4,5,6,7,8,9,10,11,12,13,14,15,16,17,18,19,20,21,22,23,24], True)
# ActiveSketch = App.getDocument('Joint_HouseMT_session_4').getObject('Sketch008')
# if ActiveSketch.ViewObject.RestoreCamera:
#   ActiveSketch.ViewObject.TempoVis.saveCamera()
#   if ActiveSketch.ViewObject.ForceOrtho:
#     ActiveSketch.ViewObject.Document.ActiveView.setCameraType('Orthographic')
# 
# Gui.Selection.addSelection('Joint_HouseMT_session_4','Body002','Pocket007.Sketch008.Edge3',1334.21,152.408,-9.53708e-10,False)
# Gui.Selection.clearSelection()
App.getDocument('Joint_HouseMT_session_4').getObject('Sketch008').delGeometries([2])
# Gui.Selection.addSelection('Joint_HouseMT_session_4','Body002','Pocket007.Sketch008.Edge6',1308.81,152.408,-9.53708e-10,False)
# Gui.Selection.clearSelection()
App.getDocument('Joint_HouseMT_session_4').getObject('Sketch008').delGeometries([5])
# Gui.runCommand('Sketcher_CreateLine',0)
ActiveSketch = App.getDocument('Joint_HouseMT_session_4').getObject('Sketch008')

lastGeoId = len(ActiveSketch.Geometry)

geoList = []
geoList.append(Part.LineSegment(App.Vector(-152.400000, 0.000000, 0.000000),App.Vector(-127.000000, 0.000000, 0.000000)))
App.getDocument('Joint_HouseMT_session_4').getObject('Sketch008').addGeometry(geoList,False)
del geoList

constraintList = []
constraintList = []
constraintList.append(Sketcher.Constraint('Coincident', 7, 1, 4, 2))
constraintList.append(Sketcher.Constraint('Coincident', 7, 2, 1, 2))
constraintList.append(Sketcher.Constraint('Horizontal', 7))
App.getDocument('Joint_HouseMT_session_4').getObject('Sketch008').addConstraint(constraintList)
del constraintList

ActiveSketch = App.getDocument('Joint_HouseMT_session_4').getObject('Sketch008')

lastGeoId = len(ActiveSketch.Geometry)

geoList = []
geoList.append(Part.LineSegment(App.Vector(-25.400000, 0.000000, 0.000000),App.Vector(0.000000, 0.000000, 0.000000)))
App.getDocument('Joint_HouseMT_session_4').getObject('Sketch008').addGeometry(geoList,False)
del geoList

constraintList = []
constraintList = []
constraintList.append(Sketcher.Constraint('Coincident', 8, 1, 2, 1))
constraintList.append(Sketcher.Constraint('Coincident', 8, 2, 3, 1))
App.getDocument('Joint_HouseMT_session_4').getObject('Sketch008').addConstraint(constraintList)
del constraintList

# Gui.getDocument('Joint_HouseMT_session_4').resetEdit()
App.ActiveDocument.recompute()
# ActiveSketch = App.getDocument('Joint_HouseMT_session_4').getObject('Sketch008')
# tv = ActiveSketch.ViewObject.TempoVis
# if tv:
#   tv.restore()
# ActiveSketch.ViewObject.TempoVis = None
# del(tv)
# del(ActiveSketch)
# 
# Gui.Selection.addSelection('Joint_HouseMT_session_4','Body002','Pocket007.Sketch008.')
App.getDocument('Joint_HouseMT_session_4').recompute()
# Gui.Selection.clearSelection()
# Gui.Selection.addSelection('Joint_HouseMT_session_4','Body002','Origin004.XY_Plane002.',1236.72,22.6564,-5.46192e-14)
# Gui.Selection.clearSelection()
# Gui.Selection.addSelection('Joint_HouseMT_session_4','Body002','Origin004.YZ_Plane002.',1219.2,21.4348,29.787)
### Begin command PartDesign_CompSketches
App.getDocument('Joint_HouseMT_session_4').getObject('Body002').newObject('Sketcher::SketchObject','Sketch011')
App.getDocument('Joint_HouseMT_session_4').getObject('Sketch011').AttachmentSupport = (App.getDocument('Joint_HouseMT_session_4').getObject('Origin004'),['YZ_Plane002.',])
App.getDocument('Joint_HouseMT_session_4').getObject('Sketch011').MapMode = 'FlatFace'
App.ActiveDocument.recompute()
# Gui.getDocument('Joint_HouseMT_session_4').setEdit(App.getDocument('Joint_HouseMT_session_4').getObject('Body002'), 0, 'Sketch011.')
# ActiveSketch = App.getDocument('Joint_HouseMT_session_4').getObject('Sketch011')
# tv = Show.TempoVis(App.ActiveDocument, tag= ActiveSketch.ViewObject.TypeId)
# ActiveSketch.ViewObject.TempoVis = tv
# if ActiveSketch.ViewObject.EditingWorkbench:
#   tv.activateWorkbench(ActiveSketch.ViewObject.EditingWorkbench)
# if ActiveSketch.ViewObject.HideDependent:
#   tv.hide(tv.get_all_dependent(App.getDocument('Joint_HouseMT_session_4').getObject('Body002'), 'Sketch011.'))
# if ActiveSketch.ViewObject.ShowSupport:
#   tv.show([ref[0] for ref in ActiveSketch.AttachmentSupport if not (ref[0].isDerivedFrom("App::Plane") or ref[0].isDerivedFrom("App::LocalCoordinateSystem"))])
# if ActiveSketch.ViewObject.ShowLinks:
#   tv.show([ref[0] for ref in ActiveSketch.ExternalGeometry])
# tv.sketchClipPlane(ActiveSketch, ActiveSketch.ViewObject.SectionView)
# tv.hide(ActiveSketch)
# del(tv)
# del(ActiveSketch)
# 
# ActiveSketch = App.getDocument('Joint_HouseMT_session_4').getObject('Sketch011')
# if ActiveSketch.ViewObject.RestoreCamera:
#   ActiveSketch.ViewObject.TempoVis.saveCamera()
#   if ActiveSketch.ViewObject.ForceOrtho:
#     ActiveSketch.ViewObject.Document.ActiveView.setCameraType('Orthographic')
# 
### End command PartDesign_CompSketches
# Gui.Selection.clearSelection()
# Gui.runCommand('Sketcher_CompCreateRectangles',0)
ActiveSketch = App.getDocument('Joint_HouseMT_session_4').getObject('Sketch011')

lastGeoId = len(ActiveSketch.Geometry)

geoList = []
geoList.append(Part.LineSegment(App.Vector(-0.861056, 0.000000, 0.000000),App.Vector(89.735329, 0.000000, 0.000000)))
geoList.append(Part.LineSegment(App.Vector(89.735329, 0.000000, 0.000000),App.Vector(89.735329, 82.789474, 0.000000)))
geoList.append(Part.LineSegment(App.Vector(89.735329, 82.789474, 0.000000),App.Vector(-0.861056, 82.789474, 0.000000)))
geoList.append(Part.LineSegment(App.Vector(-0.861056, 82.789474, 0.000000),App.Vector(-0.861056, 0.000000, 0.000000)))
App.getDocument('Joint_HouseMT_session_4').getObject('Sketch011').addGeometry(geoList,False)
del geoList

constraintList = []
constraintList.append(Sketcher.Constraint('Coincident', 0, 2, 1, 1))
constraintList.append(Sketcher.Constraint('Coincident', 1, 2, 2, 1))
constraintList.append(Sketcher.Constraint('Coincident', 2, 2, 3, 1))
constraintList.append(Sketcher.Constraint('Coincident', 3, 2, 0, 1))
constraintList.append(Sketcher.Constraint('Horizontal', 0))
constraintList.append(Sketcher.Constraint('Horizontal', 2))
constraintList.append(Sketcher.Constraint('Vertical', 1))
constraintList.append(Sketcher.Constraint('Vertical', 3))
App.getDocument('Joint_HouseMT_session_4').getObject('Sketch011').addConstraint(constraintList)
del constraintList

App.getDocument('Joint_HouseMT_session_4').getObject('Sketch011').addConstraint(Sketcher.Constraint('PointOnObject', 0, 1, -1))


# Gui.Selection.addSelection('Joint_HouseMT_session_4','Body002','Sketch011.Vertex1',1219.21,-0.861056,0,False)
# Gui.Selection.addSelection('Joint_HouseMT_session_4','Body002','Sketch011.Vertex2',1219.21,89.7353,0,False)
### Begin command Sketcher_Dimension
App.getDocument('Joint_HouseMT_session_4').getObject('Sketch011').addConstraint(Sketcher.Constraint('Distance',0,1,0,2,90.596385)) 
### End command Sketcher_Dimension
# Gui.Selection.clearSelection()
App.getDocument('Joint_HouseMT_session_4').getObject('Sketch011').addConstraint(Sketcher.Constraint('DistanceX',0,1,0,2,90.596385)) 
App.getDocument('Joint_HouseMT_session_4').Sketch011.setExpression('Constraints[9]', u'<<JoistDims>>.Depth - <<DT1>>.TongueDepth')
# Gui.Selection.addSelection('Joint_HouseMT_session_4','Body002','Sketch011.Constraint10',1219.2,9.98216,-11.72,False)
# Gui.Selection.clearSelection()
App.getDocument('Joint_HouseMT_session_4').getObject('Sketch011').delConstraint(9)
# Gui.Selection.addSelection('Joint_HouseMT_session_4','Body002','Sketch011.Vertex1',1219.21,10.0399,0,False)
App.getDocument('Joint_HouseMT_session_4').getObject('Sketch011').moveGeometries([(0, 1)], App.Vector(-8.17232, -6.1248, 0))
# Gui.runCommand('Std_Undo',0)
App.getDocument('Joint_HouseMT_session_4').getObject('Sketch011').moveGeometries([(0, 1)], App.Vector(9.98907, -8.45752, 0))
App.getDocument('Joint_HouseMT_session_4').getObject('Sketch011').moveGeometries([(0, 1)], App.Vector(21.902, -2.5755, 0))
# Gui.runCommand('Std_Undo',0)
# Gui.runCommand('Std_Undo',0)
# Gui.runCommand('Std_Undo',0)
App.getDocument('Joint_HouseMT_session_4').getObject('Sketch011').moveGeometries([(0, 2), (0, 1)], App.Vector(-0.566734, -1.13717, 0), True)
# Gui.Selection.removeSelection('Joint_HouseMT_session_4','Body002','Sketch011.Vertex1')
# Gui.Selection.addSelection('Joint_HouseMT_session_4','Body002','Sketch011.Vertex1',1219.21,9.47312,0,False)
# Gui.Selection.addSelection('Joint_HouseMT_session_4','Body002','Sketch011.V_Axis',1219.2,0,-0.356915,False)
### Begin command Sketcher_ConstrainCoincidentUnified
App.getDocument('Joint_HouseMT_session_4').getObject('Sketch011').addConstraint(Sketcher.Constraint('PointOnObject',0,1,-2))
### End command Sketcher_ConstrainCoincidentUnified
# Gui.Selection.clearSelection()
# Gui.Selection.addSelection('Joint_HouseMT_session_4','Body002','Sketch011.Vertex6',1219.19,0,82.7895,False)
# Gui.Selection.addSelection('Joint_HouseMT_session_4','Body002','Sketch011.Vertex1',1219.19,0,0,False)
### Begin command Sketcher_Dimension
App.getDocument('Joint_HouseMT_session_4').getObject('Sketch011').addConstraint(Sketcher.Constraint('Distance',2,2,0,1,82.789474)) 
### End command Sketcher_Dimension
# Gui.Selection.clearSelection()
App.getDocument('Joint_HouseMT_session_4').getObject('Sketch011').addConstraint(Sketcher.Constraint('DistanceY',0,1,2,2,82.789474)) 
App.getDocument('Joint_HouseMT_session_4').Sketch011.setExpression('Constraints[11]', u'<<DT1>>.TongueLength')
# Gui.getDocument('Joint_HouseMT_session_4').resetEdit()
App.ActiveDocument.recompute()
# ActiveSketch = App.getDocument('Joint_HouseMT_session_4').getObject('Sketch011')
# tv = ActiveSketch.ViewObject.TempoVis
# if tv:
#   tv.restore()
# ActiveSketch.ViewObject.TempoVis = None
# del(tv)
# del(ActiveSketch)
# 
# Gui.Selection.addSelection('Joint_HouseMT_session_4','Body002','Sketch011.')
App.getDocument('Joint_HouseMT_session_4').recompute()
### Begin command PartDesign_Pocket
App.getDocument('Joint_HouseMT_session_4').getObject('Body002').newObject('PartDesign::Pocket','Pocket008')
App.getDocument('Joint_HouseMT_session_4').getObject('Pocket008').Profile = (App.getDocument('Joint_HouseMT_session_4').getObject('Sketch011'), ['',])
App.getDocument('Joint_HouseMT_session_4').getObject('Pocket008').Length = 5
App.ActiveDocument.recompute()
App.getDocument('Joint_HouseMT_session_4').getObject('Pocket008').ReferenceAxis = (App.getDocument('Joint_HouseMT_session_4').getObject('Sketch011'),['N_Axis'])
App.getDocument('Joint_HouseMT_session_4').getObject('Sketch011').Visibility = False
App.ActiveDocument.recompute()
# App.getDocument('Joint_HouseMT_session_4').getObject('Pocket008').ViewObject.ShapeAppearance=getattr(App.getDocument('Joint_HouseMT_session_4').getObject('Pocket007').getLinkedObject(True).ViewObject,'ShapeAppearance',App.getDocument('Joint_HouseMT_session_4').getObject('Pocket008').ViewObject.ShapeAppearance)
# App.getDocument('Joint_HouseMT_session_4').getObject('Pocket008').ViewObject.LineColor=getattr(App.getDocument('Joint_HouseMT_session_4').getObject('Pocket007').getLinkedObject(True).ViewObject,'LineColor',App.getDocument('Joint_HouseMT_session_4').getObject('Pocket008').ViewObject.LineColor)
# App.getDocument('Joint_HouseMT_session_4').getObject('Pocket008').ViewObject.PointColor=getattr(App.getDocument('Joint_HouseMT_session_4').getObject('Pocket007').getLinkedObject(True).ViewObject,'PointColor',App.getDocument('Joint_HouseMT_session_4').getObject('Pocket008').ViewObject.PointColor)
# App.getDocument('Joint_HouseMT_session_4').getObject('Pocket008').ViewObject.Transparency=getattr(App.getDocument('Joint_HouseMT_session_4').getObject('Pocket007').getLinkedObject(True).ViewObject,'Transparency',App.getDocument('Joint_HouseMT_session_4').getObject('Pocket008').ViewObject.Transparency)
# App.getDocument('Joint_HouseMT_session_4').getObject('Pocket008').ViewObject.DisplayMode=getattr(App.getDocument('Joint_HouseMT_session_4').getObject('Pocket007').getLinkedObject(True).ViewObject,'DisplayMode',App.getDocument('Joint_HouseMT_session_4').getObject('Pocket008').ViewObject.DisplayMode)
# Gui.getDocument('Joint_HouseMT_session_4').setEdit(App.getDocument('Joint_HouseMT_session_4').getObject('Body002'), 0, 'Pocket008.')
# Gui.Selection.clearSelection()
### End command PartDesign_Pocket
# Gui.Selection.clearSelection()
App.getDocument('Joint_HouseMT_session_4').getObject('Pocket008').TaperAngle = 0.000000
App.getDocument('Joint_HouseMT_session_4').getObject('Pocket008').UseCustomVector = 0
App.getDocument('Joint_HouseMT_session_4').getObject('Pocket008').Direction = (-1, 0, 0)
App.getDocument('Joint_HouseMT_session_4').getObject('Pocket008').ReferenceAxis = (App.getDocument('Joint_HouseMT_session_4').getObject('Sketch011'), ['N_Axis'])
App.getDocument('Joint_HouseMT_session_4').getObject('Pocket008').AlongSketchNormal = 1
App.getDocument('Joint_HouseMT_session_4').getObject('Pocket008').SideType = 0
App.getDocument('Joint_HouseMT_session_4').getObject('Pocket008').Type = 1
App.getDocument('Joint_HouseMT_session_4').getObject('Pocket008').Type2 = 0
App.getDocument('Joint_HouseMT_session_4').getObject('Pocket008').UpToFace = None
App.getDocument('Joint_HouseMT_session_4').getObject('Pocket008').UpToFace2 = None
App.getDocument('Joint_HouseMT_session_4').getObject('Pocket008').Reversed = 1
App.getDocument('Joint_HouseMT_session_4').getObject('Pocket008').Offset = 0
App.getDocument('Joint_HouseMT_session_4').getObject('Pocket008').Offset2 = 0
App.getDocument('Joint_HouseMT_session_4').purgeTouched()
App.getDocument('Joint_HouseMT_session_4').recompute()
App.getDocument('Joint_HouseMT_session_4').getObject('Pocket007').Visibility = False
# Gui.getDocument('Joint_HouseMT_session_4').resetEdit()
App.getDocument('Joint_HouseMT_session_4').getObject('Sketch011').Visibility = False
# Gui.Selection.addSelection('Joint_HouseMT_session_4','Body002','Pocket008.')
# Gui.Selection.clearSelection()
# Gui.Selection.addSelection('Joint_HouseMT_session_4','Body001')
# Gui.Selection.clearSelection()
# Gui.Selection.addSelection('Joint_HouseMT_session_4','VarSet003')
FreeCAD.getDocument('Joint_HouseMT_session_4').getObject('VarSet003').TipWidth = '152.4 mm'

# Gui.runCommand('Std_Undo',0)
FreeCAD.getDocument('Joint_HouseMT_session_4').getObject('VarSet003').TipWidth = '152.4 mm'

# Gui.runCommand('Std_Undo',0)
# Gui.Selection.clearSelection()
# Gui.Selection.addSelection('Joint_HouseMT_session_4','VarSet002')
FreeCAD.getDocument('Joint_HouseMT_session_4').getObject('VarSet002').TenonLength = '203.2 mm'

# Gui.runCommand('Std_Undo',0)
# Macro End: C:\Users\Adam\Documents\Projects\BentWizard\subtractive_rework_session.FCMacro +++++++++++++++++++++++++++++++++++++++++++++++++
